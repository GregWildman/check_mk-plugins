IPI-GSLAMAG-MIB DEFINITIONS ::= BEGIN

IMPORTS
	MODULE-IDENTITY, OBJECT-TYPE
		FROM SNMPv2-SMI
	TEXTUAL-CONVENTION, RowStatus, DateAndTime
		FROM SNMPv2-TC
	ipiProductsModules
		FROM IPI-GLOBAL-REG
	ipiGslamAG
		FROM IPI-PRODUCTS-MIB
	snmpTrapServerIP, snmpTrapServerVersion, snmpTrapServerCommunity,
	snmpTrapServerPort, snmpServerCommunityHost, snmpServerCommunityValue,
	snmpServerCommunityAccessType, nameServerIP, domainServerName,
	radiusServerIP, radiusServerSecret, radiusServerTimeout, ntpServerIP,
	ntpServerKey, ntpServerVersion, ntpAuthKeyId,
	ntpAuthKeyValue, ntpTrustedKeyId, snmpServiceMode,cnOSPFAreaSizeAreaId
		FROM IPI-SERVICES-MIB
  	ospfRouterId, ospfIfIpAddress, ospfAddressLessIf, ospfIfState,
    	ospfVirtIfAreaId, ospfVirtIfNeighbor, ospfVirtIfState,
    	ospfNbrIpAddr, ospfNbrAddressLessIndex, ospfNbrRtrId,
    	ospfNbrState, ospfVirtNbrArea, ospfVirtNbrRtrId, ospfVirtNbrState,
    	ospfLsdbType, ospfLsdbLsid, ospfLsdbRouterId, ospfLsdbAreaId,
    	ospfExtLsdbLimit, ospf,
	ospfPacketSrc, ospfConfigErrorType, ospfPacketType
        	FROM OSPF-MIB
    	oampDevAuthStatus, oampDevAuthDeviceId
        	FROM IPI-OAMP-MIB;


cn4200MibModule 	MODULE-IDENTITY
	LAST-UPDATED 	"0405051400Z"
	ORGANIZATION	"CIENA Corporation"
	CONTACT-INFO
		"CIENA Support Services Contact Information

	Domestic Hotline Number - 1-800-CIENA24 (243-6224)
	International Hotline Number - Europe: 44 207 012 5500
				- Asia: 81 3 3248 4680

	Email		   - CIENA24@ciena.com
	Web		     - www.ciena.com/support/

	RMA Shipping Address:   CIENA Corporation
					900 International Drive
					Linthicum, MD  USA 21090
		 "
	DESCRIPTION
		"Copyright(C) Ciena Corporation, Inc. (2004-2006).
		This version of this MIB module is part of the Ciena enterprise
		MIBs for the CN4200 product."
	::= { ipiProductsModules 9 }

	PrimaryStateValue ::=	TEXTUAL-CONVENTION
		STATUS	current
		DESCRIPTION
			"Indicate the primary state and its qualifier for entity."
		SYNTAX
			INTEGER {
				unknown(1),
				is-nr(2),
				oos-au(3),
				oos-ma(4),
				oos-auma(5)
			}


	SecondaryStateValue ::=	TEXTUAL-CONVENTION
		STATUS	current
		DESCRIPTION
			"Indicate the primary state and its qualifier for entity."
		SYNTAX
			INTEGER {
				unknown(1),
				none(2),		-- not applicable
				ains (3),	-- auto in service
				ains-faf (4),	-- auto in service, facility failure
				ains-flt (5),	-- unassigned, fault
				ains-mea (6),	-- auto in service, mismatch of eqpt and attr
				ains-ueq (7),  -- unassigned, unequipped
				busy (8),		-- busy
				flt (9),	-- fault
				flt-busy (10),	-- fault, busy
				flt-idle (11),	-- fault, idle
				flt-mt (12),	-- fault, maintenance
				frcd (13),		-- forced back into service
				idle (14),		-- idle
				idle-busy (15),	-- idle, busy
				mea (16),	-- mismatch of eqpt and attr
				mt (17),	-- maintenance
				mt-busy (18),	-- maintenance, busy
				mt-busy-lpbk (19),	-- maintenance, busy, loopback
				mt-idle (20),	-- maintenance, idle
				mt-idle-lpbk (21),	-- maintenance, idle, loopback
				mt-ueq (22),	-- maintenance, unequipped
				psi (23),		-- protection switch inhibited. Also called 'lkdo'
				stbyc (24),	-- standby cold
				stbyh (25),	-- standby hot
				uas-eq (26),	-- unassigned, equipped
				uas-flt (27),		-- unassigned, fault
				uas-sgeo (28),	-- unassigned, supporting entity outage
				uas-ueq (29),	-- unassigned, unequipped
				ueq (30),	-- unequipped
				wrk (31),	-- working
				flt-mt-lpbk (32),	-- fault, maintenance, loopback
				mt-lpbk (33),	-- maintenance, loopback
				mt-ueq-lpbk (34),	-- maintenance, unequipped, loopback
				lpbk (35),       -- loopback
				busy-stbyc(36),	-- busy, standby cold
				busy-stbyh(37),	-- busy, standby hot
				busy-wrk(38),	-- busy, working
				idle-stbyc(39),	-- idle, standby cold
				idle-stbyh(40),	-- idle, standby hot
				idle-wrk(41),	-- idle, working
				uas(42),	-- unassigned
				ains-busy(43),	-- auto-in-service,busy
				busy-mt-flt(44),	-- busy, maintenance, fault
				degraded-stbyc(45),	-- degraded, standby cold
				degraded-stbyh(46),	-- degraded, standby hot
				degraded-wrk(47),	-- degraded, working
				busy-man(48),		-- busy, manual
				busy-degraded-wrk(49),	-- busy, degraded, working
				busy-lkdo(50),		-- busy, lockedout of protection
				busy-frcd(51),		-- busy, forced back to service
				busy-degraded-stbyh(52), -- busy, degraded, standby hot
				busy-flt-lkdo(53),	 -- busy, fault, lockedout of protection
				busy-flt-frcd(54),	 -- busy, fault, forced back to service
				ains-busy-lkdo(55),	 -- auto in service, busy, lockedout of protection
				ains-busy-frcd(56),	 -- auto in service, busy, forced back to service
				ains-lkdo(57),		 -- auto in service, lockedout of protection
				faf-lkdo(58),		 --  facility failure, locked out of protection
				mea-frcd(59),		 -- mismatch of equipment, forced back to service
				mea-lkdo(60),		 --  mismatch of equipment, locked out of protection
				idle-uas(61),		-- idle, unassigned
				man(62),		-- manual
				flt-frcd(63),		-- fault, forced back into service
				flt-psi(64),		-- fault, protection switch inhibited
                ains-busy-lpbk (65)  -- ains, busy, loopback
			}


	ActionValue ::=	TEXTUAL-CONVENTION
		STATUS	current
		DESCRIPTION
			"A command issued against a physical entity."
		SYNTAX
			INTEGER {
				init-level3(1),
				init-level6(2),
				init-level9(3),
				alw-swdx(4),
				inh-swdx(5),
				swdx-normal(6),
				swdx-forced(7),
				init-reg(8),
				opr-lpbk-facility(9),
				opr-lpbk-term(10),
				opr-lpbk-crs(11),
				rls-lpbk-facility(12),
				rls-lpbk-term(13),
				rls-lpbk-crs(14),
				remove(15),
				restore(16),
				init-level7(17),
				init-level8(18)
			}

        ProtectionSwitchCmdValue ::=	TEXTUAL-CONVENTION
		STATUS	current
		DESCRIPTION
			"Protection Switch command issued against a entity. i.e port/channel/opvcx."
		SYNTAX
			INTEGER {
				release-protected(1),
				release-protecting(2),
				lockout-of-protection(3),
				forced-switch-from-protected(4),
				forced-switch-from-protecting(5),
				manual-switch-from-protected(6),
				manual-switch-from-protecting(7)
			}

	FlagValue ::=	TEXTUAL-CONVENTION
		STATUS	current
		DESCRIPTION
			"Indicate the unknown/off/on state of a particular flag."
		SYNTAX
			INTEGER {
				unknown(1),
				off(2),
				on(3),
				not-applicable(4)
			}

	DispValue ::=	TEXTUAL-CONVENTION
		STATUS	current
		DESCRIPTION
			"Indicate the dispersion value of a Port association."
		SYNTAX
			INTEGER {
				zero(0),
            	ten(10),
            	twenty(20),
            	thirty(30),
            	fourty(40),
            	fifty(50),
            	sixty(60),
            	seventy(70),
            	eighty(80),
            	ninety(90),
            	hundred(100),
            	hundred-ten(110),
            	hundred-twenty(120),
            	hundred-fourty(140),
            	hundred-fifty(150),
            	three-hundred(300)
			}

	IfDirValue ::=	TEXTUAL-CONVENTION
		STATUS	current
		DESCRIPTION
			"Indicate the interface direction: customer facing or network facing."
		SYNTAX
			INTEGER {
				unknown(1),
				drop(2), -- customer facing
				line(3),  -- networking facing
				not-applicable(4)
			}

	TcvrReachValue ::=	TEXTUAL-CONVENTION
		STATUS	current
		DESCRIPTION
			"Indicate the range of transciever in the port."
		SYNTAX
			INTEGER {
				unknown(1),
				short-reach(2),
				intermediate-reach(3),
				long-reach(4),
				ultra-long-reach(5),
				not-applicable(6)
			}

	ShelfTypeValue ::=	TEXTUAL-CONVENTION
		STATUS	current
		DESCRIPTION
			"Indicates the shelf type of a particular shelf."
		SYNTAX
			INTEGER {
				uv-chassis(1),
				classic-chassis(2),
				micro-chassis(3),
				standalone-classic(4)	
			}

	EquipmentTypeValue ::=	TEXTUAL-CONVENTION
		STATUS	current
		DESCRIPTION
			"Indicate the equipment type of a particular entity."
		SYNTAX
			INTEGER {
				unknown(1),
				system(2),
				xc-shelf(3),
				ctrlmodule-any(4),	-- generic controller module type
				xsm(5),		-- xsm controller module
				iomodule-any(6),		-- generic IO module
				xc-gbc8(7),	-- gbc8 IO module with GIGE firmware
				xc-mxn(8),		-- mxn IO module
				xc-otu2(9),	-- otu2 IO module
				port-any(10),	-- generic port type
				elec1(11),	-- 1G electrical ethernet port
				oe1(12),		-- 1G optical ethernet port
				o10(13),		-- 10G optical ethernet port
				otu2(14),	-- G.709 compliant optical interface at OTU2 Level
				channel-any(15),	-- generic channel type
				ets1(16),		-- GigE channel,
				pfm(17),		--	power filter module
				power-supply(18),
				fan-tray(19),	-- fan tray module
				fan(20),
				mxa-shelf(21),
				mxa-ctrlr(22),  -- mxa controller module
				mxa-ctrlr-fc(23), -- mxa controller in fiber channel mode
				passive(24),	-- passive module
				eex(25),	-- 10/100 electrical ethernet port
				ofc(26),	-- fiber channel optical port
				etsx(27),	-- 10/100 channel
				mxa-ctrlr-ssm(28),  -- mxa SONET services module
				xc-fc8(29),	 -- gbc8 board with FC firmware
				oc3(30),       -- SONET/SDH oc3/stm-1 port
				oc12(31),      -- SONET/SDH oc12/stm-4 port
				oc48(32),       -- SONET/SDH oc48/stm-16 port
				xc-ps1g(33),    -- PS 1G card
				xc-ps10g(34),   -- PS 1G card
				xc-pfx80g(35),  -- Packet fabric card
				stm1(36),	-- SDH stm-1 port
				stm4(37), 	-- SDH stm-4 port
				stm16(38), 	-- SDH stm-16 port
				eex-mgmt-if(39), -- 10/100 management interfaces
				otu1(40),   -- OTU-1 port
				odu1(41),   -- ODU-1 channel
				pfx80-ctrlr(42),    -- L2 controller
				mxa-ctrlr-gps(43),  -- mxa controller in OPS mode
				cn4200-shelf(44),
				bmc(45),    -- bmc controller module
				alarm-panel(46),    -- alarm panel module
				escon(47),  -- ESCON port
				ofc2(48),   -- double rate fiber channel optical port
				opvc-any(49),  -- generic OPVC type
				opvc1(50),  -- single OPVC1
				opvc2(51),  -- 2 concatenated OPVC1s
				opvc4(52),  -- 4 concatenated OPVC1s
				opvc6(53),  -- 6 concatenated OPVC1s
				opvc7(54),  -- 7 concatenated OPVC1s
				opvc12(55), -- 12 concatenated OPVC1s
				opvc16(56),  -- 16 concatenated OPVC1s
				psm-ac130(57),
				m6s(58),
				ops(59),	-- Optical Physical Section filter
				och(60),	-- Optical Port
				monitored-filter(61),
				unmonitored-filter(62),
				psm-ac165(63), -- Pwr supp module AC 165W
				psm-dc200(64), -- Pwr supp module DC 200W
				psm-dc400(65), -- Pwr supp module DC 400W
				enhanced-alarm-panel(66), -- alarm panel enhanced
				monitored-splitter(67),
				port-filter-nw(68),  -- Optical filter network port
				port-filter-exp(69), -- Optical filter express port
				port-filter-drop(70), -- Optical filter drop port
				miscd-in(71),  -- Miscellaneous discrete in port
				miscd-out(75), -- Miscellaneous discrete out port
				f10gT(76), -- Polaris 10G transponder iomod for BAM and COT
				f10gT-ops(77), -- Polaris 10G transponder iomod with OPS for BAM and COT
				f10gT-oetune(78), -- Polaris 10G transponder iomod with OETune for BAM and COT
				f10gT-oetune-ops(79), -- Polaris 10G transponder iomod with OETune and OPS for BAM and COT
				f10gA(80), -- Polaris 10G aggr iomod for BAM and COT
				fga-ctrlrmodule(81), -- Fixed gain Amplifier controller
				vga-ctrlrmodule(82), -- Variable gain Amplifier controller
				ocm-ctrlrmodule(83), -- OCM only controller
				osc-ctrlrmodule(84), -- OSC only controller
				ops-ctrlrmodule(85), -- Optical Protection Switch controller (OPS-1)
				fga-iomodule(86), -- Fixed gain Amplifier IOMod
				vga-iomodule(87), -- Variable gain Amplifier IO Mod
				ocm-iomodule(88), -- OCM only IO Mod
				osc-iomodule(89), -- OSC only IO Mod
				ops-iomodule(90), -- Optical Protection Switch IO Mod (OPS-1)
				otu2e(91), --  11.04911 Gbps for transparent mapping of  10GbE LAN signal
				otu2f(92), --  11.27009 Gbps for mapping OFC12 signal
				odu2(93), -- odu2-channel of OTU2 port
				oe10(94), -- optical 10GE LAN, oe10
				ofc10(95), -- OFC12
				oc192(96), -- SONET/SDH OC192/STM-64 port
				stm64(97), -- SDH port: Same rate as OC192
				ocg(98), -- Optical Channel Group
				oms(99), -- Optical Multiplex Section
				ocm(100), -- Optical Channel Monitor
				dcm(101), -- Dispersion Compensation Module port
				ots(102), -- Optical Transmission Section
				stm64w(103), -- 10GbE WAN/SDH signal
				oc192w(104), -- 10GbE WAN signal
				sts192c(105), -- OC-192 channel
				vc64c(106), -- STM-64 channel
				od1v(107), -- Optical D1 video interface
				ed1v(108), -- Electrical D1 video interface
				eex1(109), -- 10/100 electrical ethernet port in cn4200
				f10gA-ops(110), -- Polaris 10G Aggregator module with OPS
				f10gA-oetune(111), -- Polaris 10G Aggregator module with OETune
				f10gA-oetune-ops(112), -- Polaris 10G Aggregator module with OETune and OPS
				osx(113),  -- Optical section Rate X: OPS module port
				ofc4(114), -- FC400 port
				opvc14(115),  -- 14 concatenated OPVC1s
				opvc24(116),  -- 24 concatenated OPVC1s
				isc2(117),  -- GDPS ISC-2
				isc3c(118),  -- GDPS ISC-3C
				isc3p(119),  -- GDPS ISC-3P
				stp(120),  -- GDPS STP
				etr(121),  -- GDPS ETR
				clo(122),  -- GDPS CLO
				fc400T(123),  -- FC400 muxponder
				etr-clo-iomodule(124),  -- ETR-CLO I/O module
				gdps-ctrlrmodule(125),  -- GDPS
				gdps-iomodule(126),  -- GDPS I/O module
				fc2(127), -- FC200 port on muxponder
				ops1-ctrlrmodule(128), -- Optical Protection Switch controller (OPS-1)
				ops1-iomodule(129), -- Optical Protection Switch IO Mod (OPS-1)
				ops2-ctrlrmodule(130), -- Optical Protection Switch controller (OPS-2)
				ops2-iomodule(131), -- Optical Protection Switch IO Mod (OPS-2)
				ops850-ctrlrmodule(132), -- Optical Protection Switch controller (OPS-850)
				ops850-iomodule(133), -- Optical Protection Switch IO Mod (OPS-850)
                cn4200mc-shelf(134),
                m3s(135),
                psm-ac450(136),
				-- ************* CTRLR MODULES FOR UV 5.0 *****************
				m3-ctrlr(138), --M3_CTRLR	
    			r5-node-ctrlr(139), --R5NODE_CTRLR
    			r5-shelf-ctrlr(140), -- R5SHELF_CTRLR 
    			dwr-ctrlr(141), -- DWR_CTRLR
    			vmux-ctrlr(142), -- VMUX_CTRLR
    			oaf-r5-ctrlr(143), -- OAF_R5_CTRLR
    			oav-r5-ctrlr(144), -- OAV_R5_CTRLR
    			man-osc-r5-ctrlr(145), -- MAN_OSC_R5_CTRLR
				-- ************* IOMOD MODULES FOR UV 5.0 *****************
				iomod-r5-oaf(146), --IPI_IOMOD_R5_OAF
     			iomod-r5-oav(147), -- IPI_IOMOD_R5_OAV
     			iomod-r5-man-osc(148), -- IPI_IOMOD_R5_MAN_OSC
     			iomod-dwr(149), -- IPI_IOMOD_DWR
     			iomod-vmux(150), -- IPI_IOMOD_VMUX
     			iomod-oaf(151), -- IPI_IOMOD_OAF
     			iomod-oav(152), -- IPI_IOMOD_OAV
     			iomod-man-osc(153), -- IPI_IOMOD_MAN_OSC
     			iomod-m3(154), -- IPI_IOMOD_M3
				-- ************* SHELF TYPES FOR UV 5.0 ***************
				cn4200rs-shelf(155), -- ROADM_SH
				cn4200rs-exp-shelf(156), -- ROADM_EXP_SH
				-- ************* POWER SUPPLY MODULE FOR UV 5.0 ***************
				psm-12v(157), -- +12V POWER ADAPTER MODULE
				-- ************* Channel Type For 5.0 *************
                occ(158), -- channel contained in OTS, OMS and OPS ports

                -- ************* module types for G10 & G10X ***************
                ctrlmodule-g10(159), -- G10_CTRLR
                ctrlmodule-g10x(160), -- G10X_CTRLR
     			iomod-g10(161), -- G10_IOMOD
     			iomod-g10x(162), -- G10X_IOMOD
				-- ************* port types for G10 & G10X ***************
     			port-pktp(163), -- PKTP
     			port-otncg(164), -- ETHP_TDM
     			port-ethp-tri-elc(165), -- ETHP_TRI_ELC
     			port-ethp-1g-elc(166), -- ETHP_1G_ELC
     			port-ethp-100-oc(167), -- ETHP_100_OC
     			port-ethp-1g-oc(168), -- ETHP_1G_OC
     			port-ethp-10g-oc(169), -- ETHP_10G_OC
     			port-ethp-any(170), -- ETHP_ANY
     			port-fp(171), -- FP_PORT
				-- ************* channel types for G10 & G10X ***************
                chan-pktch(172), -- PKTCH
                chan-tdmch(173), -- TDMCH
                chan-ethch(174), -- ETHCH
				-- ************* lport types for G10 & G10X ***************
                lport-ethlp(175), -- ETHLP
                lport-pktlp(176), -- PKTLP
                lport-ethep(177), -- ETHEP
                -- ************* CTRLR MODULES FOR REL 6.0 *****************
                oav-hp-ctrlr(178), -- OAV_R6_CTRLR
                oaf-hp-ctrlr(179), -- OAF_R6_CTRLR
                -- ************* IOMOD MODULES FOR REL 6.0 *****************
                iomod-oav-hp(180), -- IPI_IOMOD_R6_OAV
                iomod-oaf-hp(181), -- IPI_IOMOD_R6_OAF
                iomod-vmux8(182),  -- IPI_IOMOD_VMUX8
                -- ************* PDUs FOR REL 6.0 *****************
                psm-uv(183), -- IPI_MOD_POWER_UV_PSM
                psm-pdu-fuse(184), -- IPI_EQPT_PDU_FUSE
                psm-pdu-bat-feed(185), -- IPI_EQPT_PDU_BAT_FEED
                psm-pdu-rs(186), -- IPI_EQPT_PDU_RS
                psm-sh-bat-feed(187), -- IPI_EQPT_SH_BAT_FEED  
                -- ************* IOMOD MODULES FOR REL 6.1 *****************
                iomod-raman(188),  -- IPI_IOMOD_RAMAN
                psm-ac600(189), -- Pwr supp module AC 600W
                psm-dc600(190),  -- Pwr supp module DC 600W
                -- ************* RESERVED TYPES  *****************
                reserved1(191),  -- reserved
                reserved2(192),  -- reserved
                reserved3(193),  -- reserved
                reserved4(194),  -- reserved
                reserved5(195),  -- reserved
                reserved6(196),  -- reserved
                reserved7(197),  -- reserved
                reserved8(198),  -- reserved
                reserved9(199),  -- reserved
                reserved10(200),  -- reserved
                reserved11(201),  -- reserved
                reserved12(202),  -- reserved
                reserved13(203),  -- reserved
				-- ************* CnC TYPES START **************
                x4-ctrlr(204), -- X4 IOMOD
                x9-ctrlr(205), -- X9 IOMOD
                x4-iomod(206), -- X4 IOMOD
                x9-iomod(207)  -- X9 IOMOD
			}

   RemoteNodeTypeValue ::=	TEXTUAL-CONVENTION
		STATUS	current
		DESCRIPTION
			"Indicate the value of connection mode of a connection."
		SYNTAX
			INTEGER {
				ef(1),		-- ef
				cn2100(2),	-- oa
				cn2300(3),	-- mxa
				cn2200(4),	-- mx
				cn4300(5),	-- xc
				xl(6),		-- xl
				unknown(7),
				cn4350(8),	-- l2x
				cn4200(9),	-- bam
                cn4200mc(10),  -- bam
				cn4200rs(11), -- UV 
                coredirector(12), -- coredirector
                coredirectorci(13) -- coredirectorCI
			}

	WavelengthValue	::=	TEXTUAL-CONVENTION
		STATUS	current
		DESCRIPTION
			"Indicate the wavelength of a port."
		SYNTAX
		OCTET STRING (SIZE(1..64))

	RedundancyModeValue ::=	TEXTUAL-CONVENTION
		STATUS	current
		DESCRIPTION
			"Indicate the redundancy mode of a particular entity."
		SYNTAX
			INTEGER {
				unknown(1),
				not-present(2),
				primary(3),
				secondary(4),
				simplex(5)
			}

	ProtectionSwitchTypeValue ::=	TEXTUAL-CONVENTION
		STATUS	current
		DESCRIPTION
			"Indicate the value of protection switch type of a particular entity."
		SYNTAX
			INTEGER {
				unknown(1),
				not-present(2),
				one-plus-one(3),
				one-to-n(4)
			}


	ProtectionSwitchDirValue ::=	TEXTUAL-CONVENTION
		STATUS	current
		DESCRIPTION
			"Indicate the value of protection switch direction of a particular entity."
		SYNTAX
			INTEGER {
				unknown(1),
				not-present(2),
				uni-directional(3),
				bi-directional(4)
			}

	ProtectionEntityValue ::=	TEXTUAL-CONVENTION
		STATUS	current
		DESCRIPTION
			"Indicate the value of protection function of a particular entity."
		SYNTAX
			INTEGER {
				unknown(1),
				none(2),
				protected(3),
				protecting(4),
				not-applicable(5),
				protected-ring(6),
				protecting-ring(7),
				protection-source(8)
			}

	EquipmentSwitchTypeValue ::=	TEXTUAL-CONVENTION
		STATUS	current
		DESCRIPTION
			"Indicate the value of equipment switch type of a particular entity."
		SYNTAX
			INTEGER {
				unknown(1),
				not-present(2),
				normal(3),
				forced(4)
			}


	SyncSwitchCmdValue ::=	TEXTUAL-CONVENTION
		STATUS	current
		DESCRIPTION
			"Indicate the type of sync switch command. release command removes the forced or manual state.
			disable will set the sync sources in free-run mode."
		SYNTAX
			INTEGER {
				not-applicable(1),
				release(2),
				forced-switch-to-Primary(3),
				forced-switch-to-secondary(4),
				manual-switch-to-primary(5),
				manual-switch-to-secondary(6),
				disable(7)
			}

	TimeSyncStateValue ::=	TEXTUAL-CONVENTION
		STATUS	current
		DESCRIPTION
			"Indicate the sync state value of the shelf."
		SYNTAX
			INTEGER {
				unknown(1),
				enabled(2),
				disabled(3),
				forced-to-primary(4),
				forced-to-secondary(5)
			}


	ConnModeValue ::=	TEXTUAL-CONVENTION
		STATUS	current
		DESCRIPTION
			"Indicate the value of connection mode of a connection."
		SYNTAX
			INTEGER {
				unknown(1),
				not-present(2),
				uni-direction(3),
				bi-direction(4),
				loopback(5)
			}

	UMICValue ::= TEXTUAL-CONVENTION
		STATUS	current
		DESCRIPTION
			"Indicate a unique ID identifying a port or channel. Each UMIC is a 32-bit
			unsigned interger. From left (most significant) to right, we allocate 4
			bits for unit(shelf) id, 8 bits for IO module id, 8 bits for interface(port)
			id, and the rest (rightmost) 12 bits for channel id."
		SYNTAX
			Unsigned32

	LocationValue ::= TEXTUAL-CONVENTION
		STATUS		current
		DESCRIPTION
			"Indicate the location code of a physical entity."
		SYNTAX
			OCTET STRING(SIZE(0..20))

	CLEIValue ::= TEXTUAL-CONVENTION
		STATUS		current
		DESCRIPTION
			"Indicate the CLEI (common language equipment identifier) of a physical entity."
		SYNTAX
			OCTET STRING(SIZE(0..10))

	HWManufactureNameValue ::= TEXTUAL-CONVENTION
		STATUS		current
		DESCRIPTION
			"Indicate the hardware manufacture name of a physical entity."
		SYNTAX
			OCTET STRING(SIZE(0..40))

	HWManufactureSerialValue ::= TEXTUAL-CONVENTION
		STATUS		current
		DESCRIPTION
			"Indicate the hardware manufacture serial number of a physical entity."
		SYNTAX
			OCTET STRING(SIZE(1..40))

	HWRevisionValue ::= TEXTUAL-CONVENTION
		STATUS		current
		DESCRIPTION
			"Indicate the hardware revision of a physical entity."
		SYNTAX
			OCTET STRING(SIZE(1..40))

    HWPartNumberValue ::= TEXTUAL-CONVENTION
		STATUS      current
		DESCRIPTION
			"Indicate the hardware part number of a physical entity."
		SYNTAX
			OCTET STRING(SIZE(1..40))

    ConditionType ::= TEXTUAL-CONVENTION
		STATUS      current
		DESCRIPTION
			"Indicate the condition type."
		SYNTAX	INTEGER {
			unknown(1),
			ais(2),
			battery(3),
			cgm(4),
			clFan(5),
			deg(6),
			eoc(7),
			eqpt(8),
			extCont(9),
			fa(10),
			facTerm(11),
			frcdwkSwPr(12),
			freeMemLow(13),
			frngSync(14),
			hiTemp(15),
			impropRmvl(16),
			inhmsg(17),
			init(18),
			intrusion(19),
			lck(20),
			lockOutOfPr(21),
			lof(22),
			logBufrOvfl(23),
			logBufrTh(24),
			lom(25),
			lop(26),
			los(27),
			lpbkFacility(28),
			lpbkTerm(29),
			manwkSwPr(30),
			misc(31),
			ndpLnk(32),
			ndp(33),
			ntpSync(34),
			oci(35),
			osLink(36),
			pdi(37),
			plm(38),
			prcdrErr(39),
			relmig(40),
			rfi(41),
			sdBer(42),
			sfBer(43),
			sft(44),
			sftDwn(45),
			roll(46),
			sync(47),
			tuidage(48),
			tim(49),
			wtr(50),
			aco(51),
			upm(52),
			almckt(53),
			cfgerr(54),
			dataflt(55),
			exm(56),
			feed(57),
			clkSwPri(58),
			clkSwSec(59),
			intMsgErr(60),
			lfd(61),
			pwr(62),
			trmt(63),
			wkswpr(64),
			pumpcurrent1(65),
			pumpcurrent2(66),
			teccurrent1(67),
			teccurrent2(68),
			optpwrctrlfail(69),
			losp(70),
			loso(71),
			lofo(72),
			dcmfail(73),
			localflt(74),
			remoteflt(75),
			asddisabled(76),
			glocs(77),
			grdi(78),
			threshold(79),
			temperature(80),
			svcerror(81),
			aisl(82),
            timingsnc(83),
            pdufuseA1(84),
            pdufuseA8(85),
            pdufuseB7(86),
            pdubattery(87),
            lowvolt(88),
            modulepwr(89),
            deviceauth(90),
            apsd(91),
            dcmexcssloss(92),
            overload(93),
            rlos(94),
			-- ***** ESOM SUPPORT STARTS *****
			anegInProg(95), -- ANEGINPROG	Auto-negotiation In Progress
			anegLkErr(96), -- ANEGLKERR	Auto-negotiation Link Error
			anegLkFail(97), -- ANEGLKFAIL	Auto-negotiation Link Fail
			anegLkOffl(98), -- ANEGLKOFFL	Auto-negotiation Link Offline
			anegMism(99), -- ANEGMISM	Auto-negotiation Mismatch
			attrMism(100), -- ATTRMISM	Datapath Attribute Mismatch
			crdDetFail(101), -- CRDDETFAIL	Credit Detection Failure
			fltNotify(102), -- FLTNOTIFY	Fault Notification in Effect
			linkInProg(103), -- LINKINPROG	Link Initialization In Progress
			oof(104), -- OOF	Out of Frame
			rxContFlt(105), -- RXCONTFLT	Receive Continuity Fault
			txContFlt(106), -- TXCONTFLT	Transmit Continuity Fault
			uneq(107), -- UNEQ	Payload Unequipped
			vfPathFlt(108), -- VFPATHFLT	Virtual Facility Path Fault
			zeroBwAsgn(109) -- ZEROBWASGN	Zero bandwidth assigned
			-- ***** ESOM SUPPORT ENDS *****
		}

	ProtocolCapValue ::= TEXTUAL-CONVENTION
		STATUS  current
		DESCRIPTION
			"Indicate the protocol capability of the GSLAM-AG port."
		SYNTAX
			INTEGER {
				unknown(1),
				not-present(2),
				transparent(3),
				scsi(4),
				tcpip(5),
				vi(6),
				ficon(7),
				fabric(8),
				loop(9)
			}

    ClassCapValue ::= TEXTUAL-CONVENTION
		STATUS  current
		DESCRIPTION
			"Indicate the class capability of the GSLAM-AG port."
		SYNTAX
			INTEGER {
				unknown(1),
				not-present(2),
				classf(3),
				class1(4),
				class2(5),
				class3(6),
				class4(7),
				class5(8),
				class6(9),
				all(10)
			}

    MediumValue ::= TEXTUAL-CONVENTION
		STATUS  current
		DESCRIPTION
			"Indicate the medium mode of the port."
		SYNTAX
			INTEGER {
				unknown(1),
				not-present(2),
				sonet(3),
				sdh(4)
			}

	LineCodingValue ::= TEXTUAL-CONVENTION
		STATUS	current
		DESCRIPTION
			"Indicate the line coding value of the port."
		SYNTAX
			INTEGER {
				unknown(1),
				not-present(2),
				rz(3),
				nrz(4)
			}

	TimingValue ::= TEXTUAL-CONVENTION
		STATUS	current
		DESCRIPTION
			"Indicate the timing value of the port."
		SYNTAX
			INTEGER {
				unknown(1),
				not-present(2),
				internal(3),
				thru(4)
			}

	TIMModeValue ::= TEXTUAL-CONVENTION
		STATUS	current
		DESCRIPTION
			"Indicate the TIM detection mode of a particular entity."
		SYNTAX
			INTEGER {
				unknown(1),
				not-present(2),
				disable(3),
				destination(4),
				source(5),
				both(6)
			}

    PortAutoNegotiationValue ::= TEXTUAL-CONVENTION
		STATUS      current
		DESCRIPTION
			"Indicate whether the electrical/cu interface can be set to for autonegotiation for right bandwidth. "
		SYNTAX	INTEGER {
	   		unknown(1),
	   		negotiaton-off(2),
	   		negotiation-on(3),
	   		not-applicable(4)
		}

    EEPortCableTypeValue ::= TEXTUAL-CONVENTION
		STATUS      current
		DESCRIPTION
			"Indicate whether the 1000TBase port to swap signal pait to accomodate the specified type of RJ-45 cable type that is connected to the port. Applicable to copper interfacesn only."
		SYNTAX	INTEGER {
	   		unknown(1),
	   		straight(2),
	   		cross-over(3),
	   		auto-detect(4),
	   		not-applicable(5)
		}

    LaserModeValue ::= TEXTUAL-CONVENTION
		STATUS      current
		DESCRIPTION
			"Defines the laser(transmitter) bahaviour based up on detection of a failure condition on the incoming signal at an optical facility interface."
		SYNTAX	INTEGER {
	   		unknown(1),
	   		not-applicable(2),
	   		laser-auto-off(3),
	   		laser-on(4),
			laser-auto(5),
			laser-off(6)
		}

    SignalMappingValue ::= TEXTUAL-CONVENTION
		STATUS      current
		DESCRIPTION
			"Defines the mapping for transporting the 10GbE LAB client signal over OTN OTU2/OTU2e, OC-192, or STM-64 signal."
		SYNTAX	INTEGER {
	   		unknown(1),
	   		not-applicable(2),
	   		transparent(3),
	   		mac(4),
	   		mac-ocn(5),
	   		mac-preamble(6),
	   		mac-preamble-ocn(7),
			synchronous(8),
			asynchronous(9)
		}

    ModuleOperationalModeValue ::= TEXTUAL-CONVENTION
		STATUS      current
		DESCRIPTION
			"Indicates operational mode of the module "
		SYNTAX	INTEGER {
	   		unknown(1),
	   		not-present(2),
	   		none(3),
	   		repeater(4),
	   		regenerator(5),
	   		transponder(6),
	   		aggregator(7),
	   		oa-rx(8),
	   		oa-tx(9),
	   		filter-master(10),
	   		filter-slave(11),
			transponder-aggregator(12),
			fcmux-200(13),
			fcmux-400(14),
            dwr-master(15),
            dwr-slave(16),
            vmux-master(17),
            vmux-slave(18),
            oa-rx-osc(19)
		}

    EqualizationValue ::= TEXTUAL-CONVENTION
		STATUS      current
		DESCRIPTION
			"power equalization for individual channels within a band"
		SYNTAX	INTEGER {
	   		unknown(1),
	   		not-applicable(2),
	   		off(3),
	   		atoz(4),
	   		nodal(5)
		}

    AmplificationConfigModeValue ::= TEXTUAL-CONVENTION
		STATUS      current
		DESCRIPTION
			"Optical amplifier configuration for the interface"
		SYNTAX	INTEGER {
	   		unknown(1),
	   		not-applicable(2),
	   		none(3),
	   		rx-oa(4),
	   		tx-oa(5),
	   		rx-tx-oa(6),
	   		inline-amp(7)
		}

	FECValue ::=	TEXTUAL-CONVENTION
		STATUS	current
		DESCRIPTION
			"Indicate forward error correction state of the port."
		SYNTAX
			INTEGER {
				unknown(1),
				off(2),
				on(3),
				not-applicable(4),
				enhanced(5)
		}

	FreqChannelNumValue ::=	TEXTUAL-CONVENTION
		STATUS	current
		DESCRIPTION
			"Indicate frequency or channel number of a tunable port."
		SYNTAX
			INTEGER {
				unknown(1),
				not-present(2),
				-- start of obsolate enums, for now.
				lambda-850(3),
				lambda-1310(4),
				lambda-1471(5),
				lambda-1491(6),
				lambda-1511(7),
				lambda-1531(8),
				lambda-1550(9),
				lambda-1551(10),
				lambda-1571(11),
				lambda-1591(12),
				lambda-1611(13),
				-- end of obsolate/invalid enums
				-- wavelength corresponding to DWDM channel 15, 191.5 Thz
				-- 50 Ghz spacing entries are represented using -5
				lambda-ch15(14),lambda-ch15-5(15),
				lambda-ch16(16),lambda-ch16-5(17),
				lambda-ch17(18),lambda-ch17-5(19),
				lambda-ch18(20),lambda-ch18-5(21),
				lambda-ch19(22),lambda-ch19-5(23),
				lambda-ch20(24),lambda-ch20-5(25),
				lambda-ch21(26),lambda-ch21-5(27),
				lambda-ch22(28),lambda-ch22-5(29),
				lambda-ch23(30),lambda-ch23-5(31),
				lambda-ch24(32),lambda-ch24-5(33),
				lambda-ch25(34),lambda-ch25-5(35),
				lambda-ch26(36),lambda-ch26-5(37),
				lambda-ch27(38),lambda-ch27-5(39),
				lambda-ch28(40),lambda-ch28-5(41),
				lambda-ch29(42),lambda-ch29-5(43),
				lambda-ch30(44),lambda-ch30-5(45),
				lambda-ch31(46),lambda-ch31-5(47),
				lambda-ch32(48),lambda-ch32-5(49),
				lambda-ch33(50),lambda-ch33-5(51),
				lambda-ch34(52),lambda-ch34-5(53),
				lambda-ch35(54),lambda-ch35-5(55),
				lambda-ch36(56),lambda-ch36-5(57),
				lambda-ch37(58),lambda-ch37-5(59),
				lambda-ch38(60),lambda-ch38-5(61),
				lambda-ch39(62),lambda-ch39-5(63),
				lambda-ch40(64),lambda-ch40-5(65),
				lambda-ch41(66),lambda-ch41-5(67),
				lambda-ch42(68),lambda-ch42-5(69),
				lambda-ch43(70),lambda-ch43-5(71),
				lambda-ch44(72),lambda-ch44-5(73),
				lambda-ch45(74),lambda-ch45-5(75),
				lambda-ch46(76),lambda-ch46-5(77),
				lambda-ch47(78),lambda-ch47-5(79),
				lambda-ch48(80),lambda-ch48-5(81),
				lambda-ch49(82),lambda-ch49-5(83),
				lambda-ch50(84),lambda-ch50-5(85),
				lambda-ch51(86),lambda-ch51-5(87),
				lambda-ch52(88),lambda-ch52-5(89),
				lambda-ch53(90),lambda-ch53-5(91),
				lambda-ch54(92),lambda-ch54-5(93),
				lambda-ch55(94),lambda-ch55-5(95),
				lambda-ch56(96),lambda-ch56-5(97),
				lambda-ch57(98),lambda-ch57-5(99),
				lambda-ch58(100),lambda-ch58-5(101),
				lambda-ch59(102),lambda-ch59-5(103),
				lambda-ch60(104),lambda-ch60-5(105),
				lambda-ch61(106),lambda-ch61-5(107)
			}

	OPSModeValue ::=	TEXTUAL-CONVENTION
		STATUS	current
		DESCRIPTION
			"Indicate OPS mode of a OPS group"
		SYNTAX
			INTEGER {
				unknown(1),
				not-applicable(2),
				none(3),
				network(4),
				och-1310(5),
				och-1550(6),
				client-850(7),
				client-1310(8),
				client-1550(9),
				ocg(10),
				oms(11)
		}

	PCSCoding ::=	TEXTUAL-CONVENTION
		STATUS	current
		DESCRIPTION
			"Indicates McData compatibility."
		SYNTAX
			INTEGER {
				unknown(1),
				not-applicable(2),
				standard(3),
				proprietary(4)
			}

	ConsoleIFValue ::=	TEXTUAL-CONVENTION
		STATUS	current
		DESCRIPTION
			"Console interface language."
		SYNTAX
			INTEGER {
				unknown(1),
                                cli(2),
                                tl1(3)
		        }

	PortStateValue ::=	TEXTUAL-CONVENTION
		STATUS	current
		DESCRIPTION
			"Indicates port state."
		SYNTAX
			INTEGER {
                                unknown(1),
                                enabled(2),
                                disabled(3),
                                auto-enable(4)
		        }

	ChanSizeValue ::=	TEXTUAL-CONVENTION
		STATUS	current
		DESCRIPTION
			"Channel size allowed."
		SYNTAX
			INTEGER {
                                opvc0(0),
                                opvc1(1),
                                opvc2(2),
                                opvc4(4),
                                opvc6(6),
                                opvc7(7),
                                opvc12(12),
                                opvc14(14),
                                opvc16(16)
		        }

	DuplexMode ::=	TEXTUAL-CONVENTION
		STATUS	current
		DESCRIPTION
			"Duplex Mode."
		SYNTAX
			INTEGER {
                                unknown(1),
                                full-duplex(2),
                                half-duplex(3)
		        }

	-- conformance area, containing groups and compliance specifications
	ipiGslamAGConfs	OBJECT IDENTIFIER ::= { ipiGslamAG 1 }
		ipiGslamAGGroups	OBJECT IDENTIFIER ::= { ipiGslamAGConfs 1 }
		ipiGslamAGCompl	OBJECT IDENTIFIER ::= { ipiGslamAGConfs 2 }

	-- sub-tree for objects, and each functional area
	ipiGslamAGObjs 	OBJECT IDENTIFIER ::= { ipiGslamAG 2 }

   	ipiGslamAGEquipmentMgmt	OBJECT IDENTIFIER ::= { ipiGslamAGObjs 1 }
		ipiGslamAGSystemObjs				OBJECT IDENTIFIER ::= { ipiGslamAGEquipmentMgmt 1 }
   		ipiGslamAGShelfObjs					OBJECT IDENTIFIER ::= { ipiGslamAGEquipmentMgmt 2 }
   		ipiGslamAGCtrlModuleObjs			OBJECT IDENTIFIER ::= { ipiGslamAGEquipmentMgmt 3 }
   		ipiGslamAGIOModuleObjs				OBJECT IDENTIFIER ::= { ipiGslamAGEquipmentMgmt 4 }
   		ipiGslamAGPwrModuleObjs	    		OBJECT IDENTIFIER ::= { ipiGslamAGEquipmentMgmt 5 }
   		ipiGslamAGFanModuleObjs				OBJECT IDENTIFIER ::= { ipiGslamAGEquipmentMgmt 6 }
   		ipiGslamAGAlarmModuleObjs   		OBJECT IDENTIFIER ::= { ipiGslamAGEquipmentMgmt 7 }
   		ipiGslamAGPortObjs					OBJECT IDENTIFIER ::= { ipiGslamAGEquipmentMgmt 8 }
   		ipiGslamAGChannelObjs				OBJECT IDENTIFIER ::= { ipiGslamAGEquipmentMgmt 9 }
   		ipiGslamAGTimeSlotObjs      		OBJECT IDENTIFIER ::= { ipiGslamAGEquipmentMgmt 10 }
   		ipiGslamAGREL50SystemObjs     		OBJECT IDENTIFIER ::= { ipiGslamAGEquipmentMgmt 11 }
   		ipiGslamAGPduObjs     				OBJECT IDENTIFIER ::= { ipiGslamAGEquipmentMgmt 12 }

   	ipiGslamAGConnectionMgmt	OBJECT IDENTIFIER ::= { ipiGslamAGObjs 2 }
   		ipiGslamAGFabricConnectionObjs		OBJECT IDENTIFIER ::= { ipiGslamAGConnectionMgmt 1 }
  		ipiGslamAGExternalConnectionObjs	OBJECT IDENTIFIER ::= { ipiGslamAGConnectionMgmt 2 }
   		ipiGslamAGProtectionGroupObjs		OBJECT IDENTIFIER ::= { ipiGslamAGConnectionMgmt 3 }
   		ipiGslamAGTAdrMapObjs		        OBJECT IDENTIFIER ::= { ipiGslamAGConnectionMgmt 4 }
   		ipiGslamAGConcOPVCxObjs             OBJECT IDENTIFIER ::= { ipiGslamAGConnectionMgmt 5 }
   		ipiGslamAGControlConnectionObjs     OBJECT IDENTIFIER ::= { ipiGslamAGConnectionMgmt 6 }
   		ipiGslamAGPEAssociationObjs         OBJECT IDENTIFIER ::= { ipiGslamAGConnectionMgmt 7 }
		ipiGslamAGREL50ROADMPortAssocObjs	OBJECT IDENTIFIER ::= { ipiGslamAGConnectionMgmt 8 }
		ipiGslamAGREL50ROADMOpticalCXObjs		OBJECT IDENTIFIER ::= { ipiGslamAGConnectionMgmt 9 }
		ipiGslamAGREL50TopologyObjs         OBJECT IDENTIFIER ::= { ipiGslamAGConnectionMgmt 10 }
		ipiGslamAGPortAssocObjs	            OBJECT IDENTIFIER ::= { ipiGslamAGConnectionMgmt 11 }
		ipiGslamAGTopologyObjs              OBJECT IDENTIFIER ::= { ipiGslamAGConnectionMgmt 12 }
		ipiGslamAGLogicalConnectionObjs		OBJECT IDENTIFIER ::= { ipiGslamAGConnectionMgmt 13}	

	ipiGslamAGAlarmEventObjs		   OBJECT IDENTIFIER ::= { ipiGslamAGObjs 3 }
		ipiGslamAGCondAllObjs	OBJECT IDENTIFIER ::= { ipiGslamAGAlarmEventObjs 1}
		ipiGslamAGAlarmSeverity	OBJECT IDENTIFIER ::= { ipiGslamAGAlarmEventObjs 2}

	ipiGslamAGOpticalMgmt		OBJECT IDENTIFIER ::= { ipiGslamAGObjs 4 }
   		ipiGslamAGOpticalDegreeMgmtObjs     OBJECT IDENTIFIER ::= { ipiGslamAGOpticalMgmt 1 }


	-- sub-tree for notifications
	cn4200NotificationObjs		   OBJECT IDENTIFIER ::= { ipiGslamAG 3 }
		cn4200NotificationHelperObjs	OBJECT IDENTIFIER ::= { cn4200NotificationObjs 1}
		cn4200Notifications		   OBJECT IDENTIFIER ::= { cn4200NotificationObjs 2 }
		cn4200DBChangeNotifications	OBJECT IDENTIFIER ::= { cn4200NotificationObjs 3 }
		cn4200SetFailNotifications	OBJECT IDENTIFIER ::= { cn4200NotificationObjs 4 }

	-- GSLAM-AG system wide info
	gslamAGSystemName		OBJECT-TYPE
		SYNTAX		OCTET STRING(SIZE(1..20))
		MAX-ACCESS	read-only
		STATUS		current
		DESCRIPTION
			"System name assigned by TL1 interface."
	    ::= { ipiGslamAGSystemObjs 1 }


 	gslamAGSystemPrimaryState	OBJECT-TYPE
		SYNTAX PrimaryStateValue
 	 	MAX-ACCESS  read-write
 	 	STATUS      current
 	 	DESCRIPTION
			"Indicates the primary state of system."
 	 	::= { ipiGslamAGSystemObjs 2 }

 	gslamAGSystemSecondaryState	OBJECT-TYPE
		SYNTAX SecondaryStateValue
 	 	MAX-ACCESS  read-only
 	 	STATUS      current
 	 	DESCRIPTION
			"Indicates the secondary state of system."
 	 	::= { ipiGslamAGSystemObjs 3 }

  	gslamAGSystemVendorName	OBJECT-TYPE
		SYNTAX OCTET STRING(SIZE(1..40))
 	 	MAX-ACCESS  read-only
 	 	STATUS      current
 	 	DESCRIPTION
			"Indicates the vendor name of this network element."
 	 	::= { ipiGslamAGSystemObjs 4 }

  	gslamAGSystemModelName	OBJECT-TYPE
		SYNTAX OCTET STRING(SIZE(1..40))
 	 	MAX-ACCESS  read-only
 	 	STATUS      current
 	 	DESCRIPTION
			"Indicates the model name of this network element."
 	 	::= { ipiGslamAGSystemObjs 5 }

 	gslamAGSystemSoftwareIssue		OBJECT-TYPE
		SYNTAX		OCTET STRING(SIZE(1..40))
		MAX-ACCESS	read-only
		STATUS		current
		DESCRIPTION
			"Indicate the software version of this network element."
	    ::= { ipiGslamAGSystemObjs 6 }

	gslamAGSystemAction		OBJECT-TYPE
		SYNTAX		ActionValue
		MAX-ACCESS	read-write
		STATUS		current
		DESCRIPTION
			"Indicate the command issued to this network element."
	    ::= { ipiGslamAGSystemObjs 7 }

	gslamAGSystemGNE    OBJECT-TYPE
		SYNTAX	FlagValue
		MAX-ACCESS      read-write
		STATUS	  current
		DESCRIPTION
			"Indicates if GNE is enabled or disabled."
	    ::= { ipiGslamAGSystemObjs 8 }

	gslamAGSystemProxyArp    OBJECT-TYPE
		SYNTAX	FlagValue
		MAX-ACCESS      read-write
		STATUS	  current
		DESCRIPTION
			"Indicates if proxy arp is enabled or disabled for the control
			connection."
	    ::= { ipiGslamAGSystemObjs 9 }

	gslamAGSystemAutoProvisionState    OBJECT-TYPE
		SYNTAX	FlagValue
		MAX-ACCESS      read-write
		STATUS	  current
		DESCRIPTION
			"Indicates if system auto-provision is enabled or disabled."
	    ::= { ipiGslamAGSystemObjs 10 }

	gslamAGSystemRestrictDefaultRoute    OBJECT-TYPE
		SYNTAX	FlagValue
		MAX-ACCESS      read-write
		STATUS	  current
		DESCRIPTION
			"Indicate whether flooding of default route
                         information is Enabled or Disabled."
	    ::= { ipiGslamAGSystemObjs 11 }

	gslamAGSystemStaticDefaultGateway    OBJECT-TYPE
		SYNTAX	IpAddress
		MAX-ACCESS      read-only
		STATUS	  current
		DESCRIPTION
			"Indicates the static default gateway.
                         Note: This value is only valid when
                               gslamAGSystemRestrictDefaultRoute
                               is set to 'enabled'."
	    ::= { ipiGslamAGSystemObjs 12 }

	gslamAGSystemConfigChangeSeqNum    OBJECT-TYPE
		SYNTAX	Unsigned32
		MAX-ACCESS      read-only
		STATUS	  current
		DESCRIPTION
			"Indicates the current configuration change sequence number."
	    ::= { ipiGslamAGSystemObjs 13 }

    gslamAGSystemCurrentLocalTime    OBJECT-TYPE
        SYNTAX  Unsigned32
        MAX-ACCESS      read-only
        STATUS    current
        DESCRIPTION
            "Indicates the current local time in seconds elapsed sine 1970."
        ::= { ipiGslamAGSystemObjs 14 }

    gslamAGSystemOffsetFromGMT    OBJECT-TYPE
        SYNTAX Integer32 
        MAX-ACCESS      read-only
        STATUS    current
        DESCRIPTION
            "Indicates the current local time offset from GMT."
        ::= { ipiGslamAGSystemObjs 15 }

    gslamAGSystemNetmask    OBJECT-TYPE
        SYNTAX OCTET STRING(SIZE(1..40)) 
        MAX-ACCESS      read-only
        STATUS    current
        DESCRIPTION
            "Indicates the netmask of the system."
        ::= { ipiGslamAGSystemObjs 16 }

    gslamAGSystemMACAddress    OBJECT-TYPE
        SYNTAX OCTET STRING(SIZE(1..40)) 
        MAX-ACCESS      read-only
        STATUS    current
        DESCRIPTION
            "Indicates the MAC address of the system."
        ::= { ipiGslamAGSystemObjs 17 }

    gslamAGSystemDefaultGateway    OBJECT-TYPE
        SYNTAX OCTET STRING(SIZE(1..40))
        MAX-ACCESS      read-only
        STATUS    current
        DESCRIPTION
            "Indicates the default gateway of the system."
        ::= { ipiGslamAGSystemObjs 18 }

	 -- ************************ UV 5.0 START *************************
     gslamAGREL50SystemStandaloneClassic      OBJECT-TYPE
			SYNTAX      INTEGER {
                    unknown(1),
                    true(2),
                    false(3),
                    clear(4)
                }
                MAX-ACCESS  read-only
                STATUS      current
                DESCRIPTION
                        "Indicates if a system is standalone classic"
        ::= {ipiGslamAGREL50SystemObjs 1}
	
	gslamAGREL50SystemROADMOptPwrCtrl    OBJECT-TYPE
      	SYNTAX  INTEGER {
         	 unknown(1),
           	 manual(2),
           	 auto(3),
           	 not-applicable(4)
        }
       	MAX-ACCESS      read-write
       	STATUS    current
       	DESCRIPTION
           	"Indicates if system optical Auto power control is enabled or 
					disabled.Default Value is MAN"
   		::= { ipiGslamAGREL50SystemObjs 2 }

	gslamAGREL50SystemROADMNodeID   OBJECT-TYPE
       	SYNTAX  Unsigned32
       	MAX-ACCESS      read-write
       	STATUS    current
       	DESCRIPTION
           	"The nodeId is a value from 1-32. This is used to set the dither freq of the system"
       	::= { ipiGslamAGREL50SystemObjs 3 }

    gslamAGREL50SystemROADMPreEmphaisCtrl    OBJECT-TYPE
        SYNTAX  INTEGER {
             unknown(1),
             enabled(2),
             disabled(3)
        }
        MAX-ACCESS      read-write
        STATUS    current
        DESCRIPTION
            "Indicates if system pre-emphasis control is enabled or 
                    disabled. Default Value is DISABLED"
        ::= { ipiGslamAGREL50SystemObjs 4 }

	 -- ************************ UV 5.0 END *************************


	-- shelf objects
	gslamAGShelfTotalCount		OBJECT-TYPE
		SYNTAX		Unsigned32
		MAX-ACCESS	read-only
		STATUS		current
		DESCRIPTION
			"Indicate the total number of shelfs within this GSLAM-AG"
		::= {ipiGslamAGShelfObjs 1}

	gslamAGShelfTable		OBJECT-TYPE
		SYNTAX		SEQUENCE OF GslamAGShelfEntry
		MAX-ACCESS	not-accessible
		STATUS		current
		DESCRIPTION
			"A table about the shelf info of GSLAM-AG."
	    ::= { ipiGslamAGShelfObjs 2 }

	gslamAGShelfEntry OBJECT-TYPE
		SYNTAX  		GslamAGShelfEntry
		MAX-ACCESS	not-accessible
		STATUS  		current
		DESCRIPTION
			"A row in shelf table.
			Entries can't be deleted or created via SNMP ops."
		INDEX   { gslamAGShelfIndex }
	    ::= { gslamAGShelfTable 1 }

	GslamAGShelfEntry ::= SEQUENCE {
		gslamAGShelfIndex	Unsigned32,
		gslamAGShelfType		EquipmentTypeValue,
		gslamAGShelfLocation	LocationValue,
		gslamAGShelfCLEI			CLEIValue,
		gslamAGShelfPrimaryState	PrimaryStateValue,
		gslamAGShelfCtrlModuleCount	Unsigned32,
		gslamAGShelfIOModuleCount		Unsigned32,
		gslamAGShelfPwrModuleCount	Unsigned32,
		gslamAGShelfFanModuleCount		Unsigned32,
		gslamAGShelfPrimarySyncModIndex		Unsigned32,
		gslamAGShelfSecondarySyncModIndex	Unsigned32,
		gslamAGShelfActiveSyncModIndex		Unsigned32,
		gslamAGShelfSyncSwitchCmd		SyncSwitchCmdValue,
		gslamAGShelfSyncState			TimeSyncStateValue,
		gslamAGShelfInterModuleTimeSlotAvail	OCTET STRING,
		gslamAGShelfFeatureCode			OCTET STRING,
		gslamAGShelfFeatureKey			OCTET STRING,
		gslamAGShelfSerialNumber		OCTET STRING,
                gslamAGShelfConsoleIF			ConsoleIFValue,
                gslamAGShelfConsolePortState		PortStateValue
	}

	gslamAGShelfIndex	OBJECT-TYPE
		SYNTAX		Unsigned32
		MAX-ACCESS	not-accessible
		STATUS		current
		DESCRIPTION
			"Index of GSLAM-AG shelf table. It uniquely identifies each shelf."
	    ::= { gslamAGShelfEntry 1 }

	gslamAGShelfType	OBJECT-TYPE
		SYNTAX EquipmentTypeValue
 	 	MAX-ACCESS  read-only
 	 	STATUS      current
 	 	DESCRIPTION
			"Indicates the equipment type of this GSLAM-AG shelf."
 	 	::= { gslamAGShelfEntry 2 }

 	gslamAGShelfLocation	OBJECT-TYPE
		SYNTAX		LocationValue
		MAX-ACCESS	read-only
		STATUS		current
		DESCRIPTION
			"Indicate the location code of this GSLAM-AG shelf."
	    ::= { gslamAGShelfEntry 3 }

	gslamAGShelfCLEI	OBJECT-TYPE
		SYNTAX		CLEIValue
		MAX-ACCESS	read-only
		STATUS		current
		DESCRIPTION
			"Indicate the CLEI code of this GSLAM-AG shelf."
	    ::= { gslamAGShelfEntry 4 }

	 gslamAGShelfPrimaryState	OBJECT-TYPE
		SYNTAX PrimaryStateValue
 	 	MAX-ACCESS  read-only
 	 	STATUS      current
 	 	DESCRIPTION
			"Indicates the primary state of this shelf."
 	 	::= { gslamAGShelfEntry 5 }

	gslamAGShelfCtrlModuleCount	OBJECT-TYPE
		SYNTAX		Unsigned32
		MAX-ACCESS	read-only
		STATUS		current
		DESCRIPTION
			"Indicate the number of control modules (XSM) within this shelf."
	    ::= { gslamAGShelfEntry 6 }

	gslamAGShelfIOModuleCount	OBJECT-TYPE
		SYNTAX		Unsigned32
		MAX-ACCESS	read-only
		STATUS		current
		DESCRIPTION
			"Indicate the number of IO modules within this shelf."
	    ::= { gslamAGShelfEntry 7 }

	gslamAGShelfPwrModuleCount	OBJECT-TYPE
		SYNTAX		Unsigned32
		MAX-ACCESS	read-only
		STATUS		current
		DESCRIPTION
			"Indicate the number of power modules within this shelf."
	    ::= { gslamAGShelfEntry 8 }

	gslamAGShelfFanModuleCount	OBJECT-TYPE
		SYNTAX		Unsigned32
		MAX-ACCESS	read-only
		STATUS		current
		DESCRIPTION
			"Indicate the number of fan trays within this shelf."
	    ::= { gslamAGShelfEntry 9 }

        gslamAGShelfPrimarySyncModIndex	OBJECT-TYPE
		SYNTAX		Unsigned32
		MAX-ACCESS	read-write
		STATUS		current
		DESCRIPTION
			"Module index of the primary time sync source. When time sync is not provisioned
			or when the modules are in free run state, the value will be 0."
	    ::= { gslamAGShelfEntry 10 }

	gslamAGShelfSecondarySyncModIndex	OBJECT-TYPE
		SYNTAX		Unsigned32
		MAX-ACCESS	read-write
		STATUS		current
		DESCRIPTION
			"Module index of the secondary time sync source. When time sync is not provisioned
			or when the modules are in free run state, the value will be 0."
	    ::= { gslamAGShelfEntry 11 }

        gslamAGShelfActiveSyncModIndex	OBJECT-TYPE
		SYNTAX		Unsigned32
		MAX-ACCESS	read-only
		STATUS		current
		DESCRIPTION
			"Module index of the active or working time source. When time sync is not provisioned
			or when the modules are in free run state, the value will be 0."
	    ::= { gslamAGShelfEntry 12 }

	gslamAGShelfSyncSwitchCmd	OBJECT-TYPE
		SYNTAX SyncSwitchCmdValue
 	 	MAX-ACCESS  read-write
 	 	STATUS      current
 	 	DESCRIPTION
			"Indicates the sync switch command sent to IO module in the shelf. This is write-only"
 	 	::= { gslamAGShelfEntry 13 }

	gslamAGShelfSyncState	OBJECT-TYPE
		SYNTAX TimeSyncStateValue
 	 	MAX-ACCESS  read-only
 	 	STATUS      current
 	 	DESCRIPTION
			"Indicates the time sync state in the shelf."
 	 	::= { gslamAGShelfEntry 14 }

	gslamAGShelfInterModuleTimeSlotAvail      OBJECT-TYPE
       		SYNTAX      OCTET STRING(SIZE(0..1024))
       		MAX-ACCESS  read-only
       		STATUS      current
       		DESCRIPTION
       			"This object is internal to CN4200 applications to get the free available inter module
       			timeslots between all pairs of IO modules.

       			The convention used to populate time slot availability is as follows:

       			<module i>, <module j>, <free bdw i->j>, <free bdw j->i>|
       			<module m>, <module n>, <free bdw m->n>, <free bdw n->m>| ...
       			"


       	::= { gslamAGShelfEntry 15 }

	gslamAGShelfFeatureCode     OBJECT-TYPE
       		SYNTAX      OCTET STRING(SIZE(0..68))
       		MAX-ACCESS  read-write
       		STATUS      current
       		DESCRIPTION
			"Indicates a code for specific set of services in CN4200 shelf.
			 Contains all the feature codes for the chassis and each code is
			 separated by separator :"
 	 	::= { gslamAGShelfEntry 16 }

	gslamAGShelfFeatureKey     OBJECT-TYPE
       		SYNTAX      OCTET STRING(SIZE(0..88))
       		MAX-ACCESS  read-write
       		STATUS      current
       		DESCRIPTION
			"A key to enable specific set of services in CN4200 shelf. 
			Contains all the feature keys for the chassis and each key is
			separated by separator :"
 	 	::= { gslamAGShelfEntry 17 }

	gslamAGShelfSerialNumber     OBJECT-TYPE
       		SYNTAX      OCTET STRING(SIZE(0..40))
       		MAX-ACCESS  read-only
       		STATUS      current
       		DESCRIPTION
			"Indicates a chassis level vendor serial number in CN4200 shelf."
 	 	::= { gslamAGShelfEntry 18 }

        gslamAGShelfConsoleIF    OBJECT-TYPE
                SYNTAX  ConsoleIFValue
                MAX-ACCESS      read-write
                STATUS    current
                DESCRIPTION
                        "Indicates the console interface language."
                ::= { gslamAGShelfEntry 19 }

        gslamAGShelfConsolePortState    OBJECT-TYPE
                SYNTAX  PortStateValue
                MAX-ACCESS      read-write
                STATUS    current
                DESCRIPTION
                        "Indicates the state of the console port."
                ::= { gslamAGShelfEntry 20 }

	-- ************** UV 5.0 ******************
	gslamAGREL50ShelfTable		OBJECT-TYPE
		SYNTAX		SEQUENCE OF GslamAGREL50ShelfEntry
		MAX-ACCESS	not-accessible
		STATUS		current
		DESCRIPTION
			"A table about the shelf info of GSLAM-AG."
	    ::= { ipiGslamAGShelfObjs 3 }

	gslamAGREL50ShelfEntry OBJECT-TYPE
		SYNTAX  		GslamAGREL50ShelfEntry
		MAX-ACCESS	not-accessible
		STATUS  		current
		DESCRIPTION
			"A row in shelf table.
			Entries can't be deleted or created via SNMP ops."
		INDEX   { gslamAGREL50ShelfIndex }
	    ::= { gslamAGREL50ShelfTable 1 }

	GslamAGREL50ShelfEntry ::= SEQUENCE {
		gslamAGREL50ShelfIndex						Unsigned32,
		gslamAGREL50ShelfType						EquipmentTypeValue,
		gslamAGREL50ShelfLocation					LocationValue,
		gslamAGREL50ShelfCLEI						CLEIValue,
		gslamAGREL50ShelfPrimaryState				PrimaryStateValue,
		gslamAGREL50ShelfCtrlModuleCount			Unsigned32,
		gslamAGREL50ShelfIOModuleCount				Unsigned32,
		gslamAGREL50ShelfPwrModuleCount				Unsigned32,
		gslamAGREL50ShelfFanModuleCount				Unsigned32,
		gslamAGREL50ShelfSyncSwitchCmd				SyncSwitchCmdValue,
		gslamAGREL50ShelfInterModuleTimeSlotAvail   OCTET STRING,
		gslamAGREL50ShelfFeatureCode				OCTET STRING,
		gslamAGREL50ShelfFeatureKey					OCTET STRING,
		gslamAGREL50ShelfSerialNumber				OCTET STRING,
        gslamAGREL50ShelfRowStatus                  RowStatus,
        gslamAGREL50ShelfParentPortIndex            Unsigned32,
        gslamAGREL50ShelfParentShelfIndex           Unsigned32,
		gslamAGREL50ShelfUVCapable					INTEGER,
		gslamAGREL50ShelfPduValue					Unsigned32,
		gslamAGREL50ShelfPduPwrOutput				Unsigned32,
		gslamAGREL50ShelfStandaloneToUV				Unsigned32,
		gslamAGREL50ShelfPrimarySyncMod1Index		Unsigned32,
		gslamAGREL50ShelfSecondarySyncMod1Index		Unsigned32,
		gslamAGREL50ShelfActiveSyncMod1Index		Unsigned32,
		gslamAGREL50ShelfSync1State					TimeSyncStateValue,
		gslamAGREL50ShelfPrimarySyncMod2Index		Unsigned32,
		gslamAGREL50ShelfSecondarySyncMod2Index		Unsigned32,
		gslamAGREL50ShelfActiveSyncMod2Index		Unsigned32,
		gslamAGREL50ShelfSync2State					TimeSyncStateValue,
		gslamAGREL50ShelfPrimarySyncMod3Index		Unsigned32,
		gslamAGREL50ShelfSecondarySyncMod3Index		Unsigned32,
		gslamAGREL50ShelfActiveSyncMod3Index		Unsigned32,
		gslamAGREL50ShelfSync3State					TimeSyncStateValue,
		gslamAGREL50ShelfPrimarySyncMod4Index		Unsigned32,
		gslamAGREL50ShelfSecondarySyncMod4Index		Unsigned32,
		gslamAGREL50ShelfActiveSyncMod4Index		Unsigned32,
		gslamAGREL50ShelfSync4State					TimeSyncStateValue,
        gslamAGREL50ShelfConsoleIF					ConsoleIFValue,
        gslamAGREL50ShelfConsolePortState			PortStateValue
	}

	gslamAGREL50ShelfIndex	OBJECT-TYPE
		SYNTAX		Unsigned32
		MAX-ACCESS	not-accessible
		STATUS		current
		DESCRIPTION
		"Index of GSLAM-AG shelf table. It uniquely identifies each shelf."
	    ::= { gslamAGREL50ShelfEntry 1 }

	gslamAGREL50ShelfType	OBJECT-TYPE
		SYNTAX EquipmentTypeValue
 	 	MAX-ACCESS  read-only
 	 	STATUS      current
 	 	DESCRIPTION
		"Indicates the equipment type of this GSLAM-AG shelf."
 	 	::= { gslamAGREL50ShelfEntry 2 }

 	gslamAGREL50ShelfLocation	OBJECT-TYPE
		SYNTAX		LocationValue
		MAX-ACCESS	read-only
		STATUS		current
		DESCRIPTION
		"Indicate the location code of this GSLAM-AG shelf."
	    ::= { gslamAGREL50ShelfEntry 3 }

	gslamAGREL50ShelfCLEI	OBJECT-TYPE
		SYNTAX		CLEIValue
		MAX-ACCESS	read-only
		STATUS		current
		DESCRIPTION
		"Indicate the CLEI code of this GSLAM-AG shelf."
	    ::= { gslamAGREL50ShelfEntry 4 }

	 gslamAGREL50ShelfPrimaryState	OBJECT-TYPE
		SYNTAX PrimaryStateValue
 	 	MAX-ACCESS  read-only
 	 	STATUS      current
 	 	DESCRIPTION
		"Indicates the primary state of this shelf."
 	 	::= { gslamAGREL50ShelfEntry 5 }

	gslamAGREL50ShelfCtrlModuleCount	OBJECT-TYPE
		SYNTAX		Unsigned32
		MAX-ACCESS	read-only
		STATUS		current
		DESCRIPTION
		"Indicate the number of control modules (XSM) within this shelf."
	    ::= { gslamAGREL50ShelfEntry 6 }

	gslamAGREL50ShelfIOModuleCount	OBJECT-TYPE
		SYNTAX		Unsigned32
		MAX-ACCESS	read-only
		STATUS		current
		DESCRIPTION
		"Indicate the number of IO modules within this shelf."
	    ::= { gslamAGREL50ShelfEntry 7 }

	gslamAGREL50ShelfPwrModuleCount	OBJECT-TYPE
		SYNTAX		Unsigned32
		MAX-ACCESS	read-only
		STATUS		current
		DESCRIPTION
		"Indicate the number of power modules within this shelf."
	    ::= { gslamAGREL50ShelfEntry 8 }

	gslamAGREL50ShelfFanModuleCount	OBJECT-TYPE
		SYNTAX		Unsigned32
		MAX-ACCESS	read-only
		STATUS		current
		DESCRIPTION
		"Indicate the number of fan trays within this shelf."
	    ::= { gslamAGREL50ShelfEntry 9 }

	gslamAGREL50ShelfSyncSwitchCmd	OBJECT-TYPE
		SYNTAX SyncSwitchCmdValue
 	 	MAX-ACCESS  read-write
 	 	STATUS      current
 	 	DESCRIPTION
		"Indicates the sync switch command sent to IO 
			module in the shelf. This is write-only"
 	 	::= { gslamAGREL50ShelfEntry 10 }

	gslamAGREL50ShelfInterModuleTimeSlotAvail      OBJECT-TYPE
       	SYNTAX      OCTET STRING(SIZE(0..1024))
       	MAX-ACCESS  read-only
       	STATUS      current
       	DESCRIPTION
        "This object is internal to CN4200 applications
        to get the free available inter module
        timeslots between all pairs of IO modules in a
        cross-connect group.
        The convention used to populate time slot
        availability is as follows:
        <module i>, <module j>, <free bdw i->j>,
                <free bdw j->i>|
        <module m>, <module n>, <free bdw m->n>,
                <free bdw n->m>| ...
		This is how the slot numbering is divided based on 
			cross-connect group.
    	2,3,4,5|6,7,8,9|10,11,12,13|14,15,16,17
		So now we can have bw utilization like this
    	bash-2.05b# getone -v1 localhost public
				gslamAGREL50ShelfInterModuleTimeSlotAvail.1
		gslamAGREL50ShelfInterModuleTimeSlotAvail.1 = 
				2,3,0,0|2,4,0,0|2,5,0,0|
			3,4,0,0|3,5,0,0|4,5,0,0||6,7,0,0|6,8,0,0|
			6,9,0,0|7,8,0,0|7,9,0,0|
			8,9,0,0||10,11,0,0|10,12,0,0|
			10,13,0,0|11,12,0,0|11,13,0,0|12,13,0,0||
			14,15,0,0|14,16,0,0|14,17,0,0|15,16,0,0|15,17,0,0|16,17,0,0
			So we point worth noting is:
			1. A bw util is limited to modules in a cross-connect group.
			   Hence we cant have bw util between say module 5 and module 
			   6 as they are in separate cross-connect group.
			2. The two group data is separated by '||' and 
					individual value is separated by '|'."
       	::= { gslamAGREL50ShelfEntry 11 }

	gslamAGREL50ShelfFeatureCode     OBJECT-TYPE
       	SYNTAX      OCTET STRING(SIZE(0..68))
       	MAX-ACCESS  read-write
       	STATUS      current
       	DESCRIPTION
		"Indicates a code for specific set of services in 
		 CN4200 shelf.Contains all the feature codes for 
		 the chassis and each code is
		 separated by separator :"
 	 	::= { gslamAGREL50ShelfEntry 12 }

	gslamAGREL50ShelfFeatureKey     OBJECT-TYPE
       	SYNTAX      OCTET STRING(SIZE(0..88))
       	MAX-ACCESS  read-write
       	STATUS      current
       	DESCRIPTION
		"A key to enable specific set of services
		 in CN4200 shelf.Contains all the feature 
		 keys for the chassis and each key is
		 separated by separator :"
 	 	::= { gslamAGREL50ShelfEntry 13 }

	gslamAGREL50ShelfSerialNumber     OBJECT-TYPE
       	SYNTAX      OCTET STRING(SIZE(0..40))
       	MAX-ACCESS  read-only
       	STATUS      current
       	DESCRIPTION
		"Indicates a chassis level vendor serial 
			number in CN4200 shelf."
 	 	::= { gslamAGREL50ShelfEntry 14 }

	 gslamAGREL50ShelfRowStatus     OBJECT-TYPE
        SYNTAX    RowStatus
        MAX-ACCESS   read-create
        STATUS      current
        DESCRIPTION
        "Indicates kind of action performed on the object."
     	::= { gslamAGREL50ShelfEntry 15 }

     gslamAGREL50ShelfParentPortIndex     OBJECT-TYPE
        SYNTAX    Unsigned32
        MAX-ACCESS  read-write
        STATUS      current
        DESCRIPTION
        "Indicates parent port from which the shelf is sub-tended."
     	 ::= { gslamAGREL50ShelfEntry 16 }

     gslamAGREL50ShelfParentShelfIndex     OBJECT-TYPE
        SYNTAX    Unsigned32
        MAX-ACCESS  read-write
        STATUS      current
        DESCRIPTION
        "Indicates parent shelf number from which the 
		shelf is sub-tended."
     	::= { gslamAGREL50ShelfEntry 17 }

     gslamAGREL50ShelfUVCapable     OBJECT-TYPE
		SYNTAX      INTEGER {
                    not-applicable(0),
                    off(1),
                    on(2)
		}
        MAX-ACCESS  read-write
        STATUS      current
        DESCRIPTION
        "Indicates if a shelf is UV capable or not."
     	::= { gslamAGREL50ShelfEntry 18 }

     gslamAGREL50ShelfPduValue     OBJECT-TYPE
        SYNTAX    Unsigned32
        MAX-ACCESS  read-write
        STATUS      current
        DESCRIPTION
        "Indicates the PDU value[1-57]."
     	::= { gslamAGREL50ShelfEntry 19 }

     gslamAGREL50ShelfPduPwrOutput     OBJECT-TYPE
        SYNTAX    Unsigned32
        MAX-ACCESS  read-write
        STATUS      current
        DESCRIPTION
        "Indicates the PDU Power Output value[1-3]."
     	::= { gslamAGREL50ShelfEntry 20 }

     gslamAGREL50ShelfStandaloneToUV     OBJECT-TYPE
        SYNTAX    Unsigned32
        MAX-ACCESS  read-write
        STATUS      current
        DESCRIPTION
        "Indicates the standalone to uv migration.TBD"
     	::= { gslamAGREL50ShelfEntry 21 }

     gslamAGREL50ShelfPrimarySyncMod1Index	OBJECT-TYPE
		SYNTAX		Unsigned32
		MAX-ACCESS	read-write
		STATUS		current
		DESCRIPTION
		"Module index of the primary time sync
		source. When time sync is not provisioned
		or when the modules are in free run state,
		the value will be 0.This is for slot gr[1]"
	    ::= { gslamAGREL50ShelfEntry 22 }

	 gslamAGREL50ShelfSecondarySyncMod1Index	OBJECT-TYPE
		SYNTAX		Unsigned32
		MAX-ACCESS	read-write
		STATUS		current
		DESCRIPTION
		"Module index of the secondary time sync source. 
		When time sync is not provisioned
		or when the modules are in free run state, the value will be 0.
		This is for slot gr[1]"
	    ::= { gslamAGREL50ShelfEntry 23 }

     gslamAGREL50ShelfActiveSyncMod1Index	OBJECT-TYPE
		SYNTAX		Unsigned32
		MAX-ACCESS	read-only
		STATUS		current
		DESCRIPTION
		"Module index of the active or working time source. 
		When time sync is not provisioned
		or when the modules are in free run state, the value will be 0.
		This is for slot gr[1]"
	    ::= { gslamAGREL50ShelfEntry 24 }

	gslamAGREL50ShelfSync1State	OBJECT-TYPE
		SYNTAX TimeSyncStateValue
 	 	MAX-ACCESS  read-only
 	 	STATUS      current
 	 	DESCRIPTION
		"Indicates the time sync state in the shelf.
		This is for slot gr[1]"
 	 	::= { gslamAGREL50ShelfEntry 25 }

     gslamAGREL50ShelfPrimarySyncMod2Index	OBJECT-TYPE
		SYNTAX		Unsigned32
		MAX-ACCESS	read-write
		STATUS		current
		DESCRIPTION
		"Module index of the primary time sync
		source. When time sync is not provisioned
		or when the modules are in free run state,
		the value will be 0.This is for slot gr[2]"
	    ::= { gslamAGREL50ShelfEntry 26 }

	 gslamAGREL50ShelfSecondarySyncMod2Index	OBJECT-TYPE
		SYNTAX		Unsigned32
		MAX-ACCESS	read-write
		STATUS		current
		DESCRIPTION
		"Module index of the secondary time sync source. 
		When time sync is not provisioned
		or when the modules are in free run state, the value will be 0.
		This is for slot gr[2]"
	    ::= { gslamAGREL50ShelfEntry 27 }

     gslamAGREL50ShelfActiveSyncMod2Index	OBJECT-TYPE
		SYNTAX		Unsigned32
		MAX-ACCESS	read-only
		STATUS		current
		DESCRIPTION
		"Module index of the active or working time source. 
		When time sync is not provisioned
		or when the modules are in free run state, the value will be 0.
		This is for slot gr[2]"
	    ::= { gslamAGREL50ShelfEntry 28 }

	gslamAGREL50ShelfSync2State	OBJECT-TYPE
		SYNTAX TimeSyncStateValue
 	 	MAX-ACCESS  read-only
 	 	STATUS      current
 	 	DESCRIPTION
		"Indicates the time sync state in the shelf.
		This is for slot gr[2]"
 	 	::= { gslamAGREL50ShelfEntry 29 }

     gslamAGREL50ShelfPrimarySyncMod3Index	OBJECT-TYPE
		SYNTAX		Unsigned32
		MAX-ACCESS	read-write
		STATUS		current
		DESCRIPTION
		"Module index of the primary time sync
		source. When time sync is not provisioned
		or when the modules are in free run state,
		the value will be 0.This is for slot gr[3]"
	    ::= { gslamAGREL50ShelfEntry 30 }

	 gslamAGREL50ShelfSecondarySyncMod3Index	OBJECT-TYPE
		SYNTAX		Unsigned32
		MAX-ACCESS	read-write
		STATUS		current
		DESCRIPTION
		"Module index of the secondary time sync source. 
		When time sync is not provisioned
		or when the modules are in free run state, the value will be 0.
		This is for slot gr[3]"
	    ::= { gslamAGREL50ShelfEntry 31 }

     gslamAGREL50ShelfActiveSyncMod3Index	OBJECT-TYPE
		SYNTAX		Unsigned32
		MAX-ACCESS	read-only
		STATUS		current
		DESCRIPTION
		"Module index of the active or working time source. 
		When time sync is not provisioned
		or when the modules are in free run state, the value will be 0.
		This is for slot gr[3]"
	    ::= { gslamAGREL50ShelfEntry 32 }

	gslamAGREL50ShelfSync3State	OBJECT-TYPE
		SYNTAX TimeSyncStateValue
 	 	MAX-ACCESS  read-only
 	 	STATUS      current
 	 	DESCRIPTION
		"Indicates the time sync state in the shelf.
		This is for slot gr[3]"
 	 	::= { gslamAGREL50ShelfEntry 33 }

     gslamAGREL50ShelfPrimarySyncMod4Index	OBJECT-TYPE
		SYNTAX		Unsigned32
		MAX-ACCESS	read-write
		STATUS		current
		DESCRIPTION
		"Module index of the primary time sync
		source. When time sync is not provisioned
		or when the modules are in free run state,
		the value will be 0.This is for slot gr[4]"
	    ::= { gslamAGREL50ShelfEntry 34 }

	 gslamAGREL50ShelfSecondarySyncMod4Index	OBJECT-TYPE
		SYNTAX		Unsigned32
		MAX-ACCESS	read-write
		STATUS		current
		DESCRIPTION
		"Module index of the secondary time sync source. 
		When time sync is not provisioned
		or when the modules are in free run state, the value will be 0.
		This is for slot gr[4]"
	    ::= { gslamAGREL50ShelfEntry 35 }

     gslamAGREL50ShelfActiveSyncMod4Index	OBJECT-TYPE
		SYNTAX		Unsigned32
		MAX-ACCESS	read-only
		STATUS		current
		DESCRIPTION
		"Module index of the active or working time source. 
		When time sync is not provisioned
		or when the modules are in free run state, the value will be 0.
		This is for slot gr[4]"
	    ::= { gslamAGREL50ShelfEntry 36 }

	gslamAGREL50ShelfSync4State	OBJECT-TYPE
		SYNTAX TimeSyncStateValue
 	 	MAX-ACCESS  read-only
 	 	STATUS      current
 	 	DESCRIPTION
		"Indicates the time sync state in the shelf.
		This is for slot gr[4]"
 	 	::= { gslamAGREL50ShelfEntry 37 }

     gslamAGREL50ShelfConsoleIF    OBJECT-TYPE
        SYNTAX  ConsoleIFValue
        MAX-ACCESS      read-write
        STATUS    current
        DESCRIPTION
        "Indicates the console interface language."
        ::= { gslamAGREL50ShelfEntry 38 }

     gslamAGREL50ShelfConsolePortState    OBJECT-TYPE
        SYNTAX  PortStateValue
        MAX-ACCESS      read-write
        STATUS    current
        DESCRIPTION
        "Indicates the state of the console port."
        ::= { gslamAGREL50ShelfEntry 39 }

	-- ********** PDU TABLE START *************
	gslamAGPduTable		OBJECT-TYPE
		SYNTAX		SEQUENCE OF GslamAGPduEntry
		MAX-ACCESS	not-accessible
		STATUS		current
		DESCRIPTION
			"A table about the PDU info of GSLAM-AG."
	    ::= { ipiGslamAGPduObjs 1 }

	gslamAGPduEntry OBJECT-TYPE
		SYNTAX  		GslamAGPduEntry
		MAX-ACCESS	not-accessible
		STATUS  		current
		DESCRIPTION
			"A row in pdu table.  Entries can't be deleted 
			 or created via SNMP ops."
		INDEX   { gslamAGPduIndex }
	    ::= { gslamAGPduTable 1 }

	GslamAGPduEntry ::= SEQUENCE {
		gslamAGPduIndex		Unsigned32,
		gslamAGPduPort1		Unsigned32,
		gslamAGPduPort2		Unsigned32,
		gslamAGPduPort3 	Unsigned32,
		gslamAGPduState		INTEGER
	}

	gslamAGPduIndex	OBJECT-TYPE
		SYNTAX		Unsigned32
		MAX-ACCESS	not-accessible
		STATUS		current
		DESCRIPTION
		"Index of GSLAM-AG Pdu table. It uniquely identifies each pdu."
	    ::= { gslamAGPduEntry 1 }

	gslamAGPduPort1	OBJECT-TYPE
		SYNTAX 		Unsigned32
 	 	MAX-ACCESS  read-only
 	 	STATUS      current
 	 	DESCRIPTION
		"Indicates the shelfid [1-57] power feed 1 is supplying power to."
 	 	::= { gslamAGPduEntry 2 }

	gslamAGPduPort2	OBJECT-TYPE
		SYNTAX 		Unsigned32
 	 	MAX-ACCESS  read-only
 	 	STATUS      current
 	 	DESCRIPTION
		"Indicates the shelfid [1-57] power feed 2 is supplying power to."
 	 	::= { gslamAGPduEntry 3 }

	gslamAGPduPort3	OBJECT-TYPE
		SYNTAX 		Unsigned32
 	 	MAX-ACCESS  read-only
 	 	STATUS      current
 	 	DESCRIPTION
		"Indicates the shelfid [1-57] power feed 3 is supplying power to."
 	 	::= { gslamAGPduEntry 4 }

	gslamAGPduState	OBJECT-TYPE
		SYNTAX      INTEGER {
			unknown (0), 
			is-nr (1),
			oos-au (2)
		}
 	 	MAX-ACCESS  read-only
 	 	STATUS      current
 	 	DESCRIPTION
		"Indicates the state of the pdu"
 	 	::= { gslamAGPduEntry 5 }

	-- ********** PDU TABLE END *************

	-- controller objects
	gslamAGCtrlModuleTable		OBJECT-TYPE
		SYNTAX		SEQUENCE OF GslamAGCtrlModuleEntry
		MAX-ACCESS	not-accessible
		STATUS		deprecated
		DESCRIPTION
			"A table about the controller modules of GSLAM-AG."
	    ::= { ipiGslamAGCtrlModuleObjs 1 }

	gslamAGCtrlModuleEntry OBJECT-TYPE
		SYNTAX  		GslamAGCtrlModuleEntry
		MAX-ACCESS	not-accessible
		STATUS  		deprecated
		DESCRIPTION
			"A row in module table.
			Entries can't be deleted or created via SNMP ops."
		INDEX   { gslamAGShelfIndex, gslamAGCtrlModuleIndex }
	    ::= { gslamAGCtrlModuleTable 1 }

	GslamAGCtrlModuleEntry ::= SEQUENCE {
		gslamAGCtrlModuleIndex		Unsigned32,
		gslamAGCtrlModuleType		EquipmentTypeValue,
		gslamAGCtrlModuleAction			ActionValue,
		gslamAGCtrlModuleLocation		LocationValue,
		gslamAGCtrlModuleCLEI		CLEIValue,
		gslamAGCtrlModulePrimaryState		PrimaryStateValue,
		gslamAGCtrlModuleSecondaryState		PrimaryStateValue,
		gslamAGCtrlModuleRedundancyMode		RedundancyModeValue,
		gslamAGCtrlModuleHWManufactureName	HWManufactureNameValue,
		gslamAGCtrlModuleHWManufactureSerial	HWManufactureSerialValue,
		gslamAGCtrlModuleHWRevision		HWRevisionValue,
		gslamAGCtrlModuleHWManufacturePartName HWPartNumberValue,
		gslamAGCtrlModuleHWManufacturePartNumber HWPartNumberValue
	}

	gslamAGCtrlModuleIndex	OBJECT-TYPE
		SYNTAX		Unsigned32
		MAX-ACCESS	not-accessible
		STATUS		deprecated
		DESCRIPTION
			"Index of GSLAM-AG controller module table. It uniquely identifies each module."
	    ::= { gslamAGCtrlModuleEntry 1 }

	gslamAGCtrlModuleType	OBJECT-TYPE
		SYNTAX EquipmentTypeValue
 	 	MAX-ACCESS  read-only
 	 	STATUS      deprecated
 	 	DESCRIPTION
			"Indicates the equipment type of this controller module."
 	 	::= { gslamAGCtrlModuleEntry 2 }

	gslamAGCtrlModuleAction			OBJECT-TYPE
		SYNTAX		ActionValue
		MAX-ACCESS	read-write
		STATUS		deprecated
		DESCRIPTION
			"Indicate command issued to this GSLAM-AG controller module."
	    ::= { gslamAGCtrlModuleEntry 3 }

	gslamAGCtrlModuleLocation		OBJECT-TYPE
		SYNTAX		LocationValue
		MAX-ACCESS	read-only
		STATUS		deprecated
		DESCRIPTION
			"Indicate the location code of this GSLAM-AG controller module."
	    ::= { gslamAGCtrlModuleEntry 4 }

	gslamAGCtrlModuleCLEI		OBJECT-TYPE
		SYNTAX		CLEIValue
		MAX-ACCESS	read-only
		STATUS		deprecated
		DESCRIPTION
			"Indicate the CLEI code of this GSLAM-AG controller module."
	    ::= { gslamAGCtrlModuleEntry 5 }

	gslamAGCtrlModulePrimaryState	OBJECT-TYPE
		SYNTAX	PrimaryStateValue
 	 	MAX-ACCESS  read-only
 	 	STATUS      deprecated
 	 	DESCRIPTION
			"Indicates the primary state of this GSLAM-AG controller module."
 	 	::= { gslamAGCtrlModuleEntry 6 }

	gslamAGCtrlModuleSecondaryState	OBJECT-TYPE
		SYNTAX	SecondaryStateValue
 	 	MAX-ACCESS  read-only
 	 	STATUS      deprecated
 	 	DESCRIPTION
			"Indicates the secondary state of this GSLAM-AG controller module."
 	 	::= { gslamAGCtrlModuleEntry 7 }

	gslamAGCtrlModuleRedundancyMode	OBJECT-TYPE
		SYNTAX	RedundancyModeValue
 	 	MAX-ACCESS  read-only
 	 	STATUS      deprecated
 	 	DESCRIPTION
			"Indicates the redundancy mode of this GSLAM-AG controller module."
 	 	::= { gslamAGCtrlModuleEntry 8 }

	gslamAGCtrlModuleHWManufactureName		OBJECT-TYPE
		SYNTAX		HWManufactureNameValue
		MAX-ACCESS	read-only
		STATUS		deprecated
		DESCRIPTION
			"Indicate hardware manufacture name of this GSLAM-AG controller module."
	    ::= { gslamAGCtrlModuleEntry 9 }

	gslamAGCtrlModuleHWManufactureSerial		OBJECT-TYPE
		SYNTAX		HWManufactureSerialValue
		MAX-ACCESS	read-only
		STATUS		deprecated
		DESCRIPTION
			"Indicate hardware manufacture serial number of this GSLAM-AG controller module."
	    ::= { gslamAGCtrlModuleEntry 10 }

	gslamAGCtrlModuleHWRevision		OBJECT-TYPE
		SYNTAX		HWRevisionValue
		MAX-ACCESS	read-only
		STATUS		deprecated
		DESCRIPTION
			"Indicate hardware revision of this GSLAM-AG controller module."
	    ::= { gslamAGCtrlModuleEntry 11 }

	gslamAGCtrlModuleHWManufacturePartName	OBJECT-TYPE
		SYNTAX      HWPartNumberValue
		MAX-ACCESS  read-only
		STATUS      deprecated
		DESCRIPTION
			"Indicate hardware manufacture part name about this
			GSLAM-AG controller module."
		::= { gslamAGCtrlModuleEntry 12 }

	gslamAGCtrlModuleHWManufacturePartNumber      OBJECT-TYPE
		SYNTAX      HWPartNumberValue
		MAX-ACCESS  read-only
		STATUS      deprecated
		DESCRIPTION
			"Indicate hardware manufacture part number about this
			GSLAM-AG controller module."
		::= { gslamAGCtrlModuleEntry 13 }

	-- IO module objects
	gslamAGIOModuleTable		OBJECT-TYPE
		SYNTAX		SEQUENCE OF GslamAGIOModuleEntry
		MAX-ACCESS	not-accessible
		STATUS		current
		DESCRIPTION
			"A table about the IO modules of GSLAM-AG."
	    ::= { ipiGslamAGIOModuleObjs 1 }

	gslamAGIOModuleEntry OBJECT-TYPE
		SYNTAX  		GslamAGIOModuleEntry
		MAX-ACCESS	not-accessible
		STATUS  		current
		DESCRIPTION
			"A row in module table.
			Entries can't be deleted or created via SNMP ops."
		INDEX   { gslamAGShelfIndex, gslamAGIOModuleIndex }
	    ::= { gslamAGIOModuleTable 1 }

	GslamAGIOModuleEntry ::= SEQUENCE {
		gslamAGIOModuleIndex			Unsigned32,
		gslamAGIOModuleType			EquipmentTypeValue,
		gslamAGIOModuleAction			ActionValue,
		gslamAGIOModuleRowStatus		RowStatus,
		gslamAGIOModuleLocation			LocationValue,
		gslamAGIOModuleCLEI			CLEIValue,
		gslamAGIOModulePrimaryState		PrimaryStateValue,
		gslamAGIOModuleSecondaryState		SecondaryStateValue,
		gslamAGIOModuleHWManufactureName	HWManufactureNameValue,
		gslamAGIOModuleHWManufactureSerial	HWManufactureSerialValue,
		gslamAGIOModuleHWRevision		HWRevisionValue,
		gslamAGIOModuleHWManufacturePartName  HWPartNumberValue,
		gslamAGIOModuleHWManufacturePartNumber HWPartNumberValue,
		gslamAGIOModuleOperationalMode		ModuleOperationalModeValue,
		gslamAGIOModuleAutoShutdown		FlagValue,
		gslamAGIOModuleDegreeId			Unsigned32,
		gslamAGIOModuleGain			OCTET STRING,
		gslamAGIOModulePump1ActualLBC		OCTET STRING,
		gslamAGIOModulePump2ActualLBC		OCTET STRING,
		gslamAGIOModulePump1KinkFreeCurrent	OCTET STRING,
		gslamAGIOModulePump2KinkFreeCurrent	OCTET STRING,
		gslamAGIOModuleOPSGroup1OPSMode		OPSModeValue,
		gslamAGIOModuleOPSGroup1LOPMode		FlagValue,
		gslamAGIOModuleOPSGroup2OPSMode		OPSModeValue,
		gslamAGIOModuleOPSGroup2LOPMode		FlagValue,
		gslamAGIOModuleFeatureCode		OCTET STRING,
		gslamAGIOModuleFeatureKey		OCTET STRING,
        gslamAGIOModuleDCFLossBorrowing      INTEGER,
        gslamAGIOModuleFiberTiltCompensation INTEGER,
        gslamAGIOModuleOPLaserState          INTEGER,
        gslamAGIOModuleActualOPLaserState    INTEGER,
        gslamAGIOModuleDCMType               CLEIValue,             
        gslamAGIOModuleGainTCAThreshold      OCTET STRING,
        gslamAGIOModuleLaserStatus           INTEGER,
        gslamAGIOModulePump3ActualLBC        OCTET STRING,
        gslamAGIOModulePump3KinkFreeCurrent  OCTET STRING,
        gslamAGIOModule1425PumpPower         OCTET STRING,
        gslamAGIOModule1455PumpPower         OCTET STRING,
        gslamAGIOModuleTECCurrentPump1       OCTET STRING,
        gslamAGIOModuleTECCurrentPump2       OCTET STRING,
        gslamAGIOModuleTECCurrentPump3       OCTET STRING,
        gslamAGIOModulePump1SubmountTemp     OCTET STRING,
        gslamAGIOModulePump2SubmountTemp     OCTET STRING,
        gslamAGIOModulePump3SubmountTemp     OCTET STRING
	}

	gslamAGIOModuleIndex	OBJECT-TYPE
		SYNTAX		Unsigned32
		MAX-ACCESS	not-accessible
		STATUS		current
		DESCRIPTION
			"Index of GSLAM-AG IO module table. It uniquely identifies each module."
	    ::= { gslamAGIOModuleEntry 1 }

	gslamAGIOModuleType	OBJECT-TYPE
		SYNTAX EquipmentTypeValue
 	 	MAX-ACCESS  read-write
 	 	STATUS      current
 	 	DESCRIPTION
			"Indicates the equipment type of this IO module."
 	 	::= { gslamAGIOModuleEntry 2 }

	gslamAGIOModuleRowStatus		OBJECT-TYPE
		SYNTAX		RowStatus
		MAX-ACCESS	read-create
		STATUS		current
		DESCRIPTION
			"Current status of this GSLAM-AG IO module entry."
    	::= { gslamAGIOModuleEntry 3 }

	gslamAGIOModuleAction			OBJECT-TYPE
		SYNTAX		ActionValue
		MAX-ACCESS	read-write
		STATUS		current
		DESCRIPTION
			"Indicate command issued to this GSLAM-AG IO module."
	    ::= { gslamAGIOModuleEntry 4 }

	gslamAGIOModuleLocation		OBJECT-TYPE
		SYNTAX		LocationValue
		MAX-ACCESS	read-only
		STATUS		current
		DESCRIPTION
			"Indicate the location code of this GSLAM-AG IO module."
	    ::= { gslamAGIOModuleEntry 5 }

	gslamAGIOModuleCLEI		OBJECT-TYPE
		SYNTAX		CLEIValue
		MAX-ACCESS	read-write
		STATUS		current
		DESCRIPTION
			"Indicate the CLEI code of this GSLAM-AG IO module."
	    ::= { gslamAGIOModuleEntry 6 }

	gslamAGIOModulePrimaryState	OBJECT-TYPE
		SYNTAX	PrimaryStateValue
 	 	MAX-ACCESS  read-write
 	 	STATUS      current
 	 	DESCRIPTION
			"Indicates the primary state of this IO module."
 	 	::= { gslamAGIOModuleEntry 7 }

	gslamAGIOModuleSecondaryState	OBJECT-TYPE
		SYNTAX	SecondaryStateValue
 	 	MAX-ACCESS  read-only
 	 	STATUS      current
 	 	DESCRIPTION
			"Indicates the secondary state of this IO module."
 	 	::= { gslamAGIOModuleEntry 8 }

	gslamAGIOModuleHWManufactureName		OBJECT-TYPE
		SYNTAX		HWManufactureNameValue
		MAX-ACCESS	read-only
		STATUS		current
		DESCRIPTION
			"Indicate hardware manufacture name of this GSLAM-AG IO module."
	    ::= { gslamAGIOModuleEntry 9 }

	gslamAGIOModuleHWManufactureSerial		OBJECT-TYPE
		SYNTAX		HWManufactureSerialValue
		MAX-ACCESS	read-only
		STATUS		current
		DESCRIPTION
			"Indicate hardware manufacture serial number of this GSLAM-AG IO module."
	    ::= { gslamAGIOModuleEntry 10 }

	gslamAGIOModuleHWRevision		OBJECT-TYPE
		SYNTAX		HWRevisionValue
		MAX-ACCESS	read-only
		STATUS		current
		DESCRIPTION
			"Indicate hardware revision of this GSLAM-AG IO module."
	    ::= { gslamAGIOModuleEntry 11 }

	gslamAGIOModuleHWManufacturePartName	OBJECT-TYPE
		SYNTAX      HWPartNumberValue
		MAX-ACCESS  read-only
		STATUS      current
		DESCRIPTION
			"Indicate hardware manufacture part name about this
			GSLAM-AG IO module."
		::= { gslamAGIOModuleEntry 12 }

	gslamAGIOModuleHWManufacturePartNumber      OBJECT-TYPE
		SYNTAX      HWPartNumberValue
		MAX-ACCESS  read-only
		STATUS      current
		DESCRIPTION
			"Indicate hardware manufacture part number about this
			GSLAM-AG IO module."
		::= { gslamAGIOModuleEntry 13 }

	gslamAGIOModuleOperationalMode      OBJECT-TYPE
		SYNTAX      ModuleOperationalModeValue
		MAX-ACCESS  read-write
		STATUS      current
		DESCRIPTION
			"Defines module operational mode of GSLAM-AG IO module."
		::= { gslamAGIOModuleEntry 14 }

	gslamAGIOModuleAutoShutdown      OBJECT-TYPE
		SYNTAX      FlagValue
		MAX-ACCESS  read-write
		STATUS      deprecated 
		DESCRIPTION
			"Indicates Automatic shutdown of Optical Amplifier upon
			 detection of input signal loss."
		::= { gslamAGIOModuleEntry 15 }

	gslamAGIOModuleDegreeId      OBJECT-TYPE
		SYNTAX      Unsigned32
		MAX-ACCESS  read-write
		STATUS      current
		DESCRIPTION
			"Indicates association of a Optical module with a degree."
		::= { gslamAGIOModuleEntry 16 }

	gslamAGIOModuleGain      OBJECT-TYPE
		SYNTAX      OCTET STRING(SIZE(1..8))
		MAX-ACCESS  read-write
		STATUS      current
		DESCRIPTION
			"Defines Optical gain (or module level gain,Gtotal) for a variable gain optical amplifier"
		::= { gslamAGIOModuleEntry 17 }

	gslamAGIOModulePump1ActualLBC      OBJECT-TYPE
		SYNTAX      OCTET STRING(SIZE(1..8))
		MAX-ACCESS  read-only
		STATUS      current
		DESCRIPTION
			"Laser pump 1 actual LBC value in DB"
		::= { gslamAGIOModuleEntry 18 }

	gslamAGIOModulePump2ActualLBC      OBJECT-TYPE
		SYNTAX      OCTET STRING(SIZE(1..8))
		MAX-ACCESS  read-only
		STATUS      current
		DESCRIPTION
			"Laser pump 2 actual LBC value in DB"
		::= { gslamAGIOModuleEntry 19 }

	gslamAGIOModulePump1KinkFreeCurrent      OBJECT-TYPE
		SYNTAX      OCTET STRING(SIZE(1..8))
		MAX-ACCESS  read-only
		STATUS      current
		DESCRIPTION
			"Laser pump 1 monitored LBC value in DB"
		::= { gslamAGIOModuleEntry 20 }

	gslamAGIOModulePump2KinkFreeCurrent      OBJECT-TYPE
		SYNTAX      OCTET STRING(SIZE(1..8))
		MAX-ACCESS  read-only
		STATUS      current
		DESCRIPTION
			"Laser pump 2 monitored LBC value in DB"
		::= { gslamAGIOModuleEntry 21 }

	gslamAGIOModuleOPSGroup1OPSMode      OBJECT-TYPE
		SYNTAX      OPSModeValue
		MAX-ACCESS  read-write
		STATUS      current
		DESCRIPTION
			"OPS mode of OPS group 1"
		::= { gslamAGIOModuleEntry 22 }

	gslamAGIOModuleOPSGroup1LOPMode      OBJECT-TYPE
		SYNTAX      FlagValue
		MAX-ACCESS  read-write
		STATUS      current
		DESCRIPTION
			"Loss of power mode for OPS group 1"
		::= { gslamAGIOModuleEntry 23 }

	gslamAGIOModuleOPSGroup2OPSMode      OBJECT-TYPE
		SYNTAX      OPSModeValue
		MAX-ACCESS  read-write
		STATUS      current
		DESCRIPTION
			"OPS mode of OPS group 2"
		::= { gslamAGIOModuleEntry 24 }

	gslamAGIOModuleOPSGroup2LOPMode      OBJECT-TYPE
		SYNTAX      FlagValue
		MAX-ACCESS  read-write
		STATUS      current
		DESCRIPTION
			"Loss of power mode for OPS group 2"
		::= { gslamAGIOModuleEntry 25 }

	gslamAGIOModuleFeatureCode     OBJECT-TYPE
       		SYNTAX      OCTET STRING(SIZE(0..40))
       		MAX-ACCESS  read-write
       		STATUS      current
       		DESCRIPTION
				"Indicates a code for specific set of services in CN4200 shelf."
 	 	::= { gslamAGIOModuleEntry 26 }

	gslamAGIOModuleFeatureKey     OBJECT-TYPE
       		SYNTAX      OCTET STRING(SIZE(0..40))
       		MAX-ACCESS  read-write
       		STATUS      current
       		DESCRIPTION
				"A key to enable specific set of services in CN4200 shelf.
				This is write only parameter at module level"
 	 	::= { gslamAGIOModuleEntry 27 }

    gslamAGIOModuleDCFLossBorrowing     OBJECT-TYPE
        SYNTAX  INTEGER {
             not-applicable(1),
             enabled(2),
             disabled(3)
        }
        MAX-ACCESS      read-write
        STATUS    current
        DESCRIPTION
            "Indicates if module loss borrowing is enabled or disabled. 
             Default Value is DISABLED for OAV-VS-U-CP"
        ::= { gslamAGIOModuleEntry 28 }

    gslamAGIOModuleFiberTiltCompensation OBJECT-TYPE
        SYNTAX      INTEGER {
            not-applicable(1),
            enabled (2),
            disabled (3)
        }

        MAX-ACCESS  read-write
        STATUS      current
        DESCRIPTION
            "Fiber Tilt compensation provisioning in stand-alone classic shelf .
             Default Value depends on module type."
        ::= { gslamAGIOModuleEntry 29}

    gslamAGIOModuleOPLaserState  OBJECT-TYPE
        SYNTAX      INTEGER {
            laser-state-not-present (0), --unsupport fiber type 
            laser-state-auto (1),
            laser-state-off (2),
            laser-state-on (3)
        }
        MAX-ACCESS  read-write
        STATUS      current
        DESCRIPTION
            "Indicates laser mode of Optical Amplifier upon detection
             of input signal loss. This is replacing the autoshutdown flag"
        ::= { gslamAGIOModuleEntry 30 }

    gslamAGIOModuleActualOPLaserState OBJECT-TYPE
        SYNTAX      INTEGER {
            laser-state-not-present (0), --unsupport fiber type 
            laser-state-on (1),
            laser-state-off (2)
        }
        MAX-ACCESS read-only
        STATUS      current
        DESCRIPTION
            "Indicates actual OA laser mode of CN4200 Optical Amplifier."
        ::= { gslamAGIOModuleEntry 31 }

    gslamAGIOModuleDCMType     OBJECT-TYPE
        SYNTAX      CLEIValue
        MAX-ACCESS  read-write
        STATUS      current
        DESCRIPTION
            "Indicate the CLEI code of DCM."
        ::= { gslamAGIOModuleEntry 32 }

    gslamAGIOModuleGainTCAThreshold     OBJECT-TYPE
        SYNTAX  OCTET STRING(SIZE(1..8))
        MAX-ACCESS      read-write
        STATUS    current
        DESCRIPTION
            "Gain TCA value for Raman module in dB "
        ::= { gslamAGIOModuleEntry 33 }

    gslamAGIOModuleLaserStatus     OBJECT-TYPE
        SYNTAX  INTEGER {
             not-applicable(1),
             off(2),
             on(3)
        }
        MAX-ACCESS      read-only
        STATUS    current
        DESCRIPTION
            "Indicates if the laser is on or off for an amplifier"
        ::= { gslamAGIOModuleEntry 34 }

    gslamAGIOModulePump3ActualLBC      OBJECT-TYPE
           SYNTAX      OCTET STRING(SIZE(1..8))
           MAX-ACCESS  read-only
           STATUS      current
           DESCRIPTION
                   "Laser pump 3 actual LBC value in DB"
           ::= { gslamAGIOModuleEntry 35 }

    gslamAGIOModulePump3KinkFreeCurrent      OBJECT-TYPE
           SYNTAX      OCTET STRING(SIZE(1..8))
           MAX-ACCESS  read-only
           STATUS      current
           DESCRIPTION
                   " Kink Free Current Pump3 in DB"
           ::= { gslamAGIOModuleEntry 36 }

    gslamAGIOModule1425PumpPower      OBJECT-TYPE
           SYNTAX      OCTET STRING(SIZE(1..8))
           MAX-ACCESS  read-only
           STATUS      current
           DESCRIPTION
                   " 1425nm Pump Power  in DB"
           ::= { gslamAGIOModuleEntry 37 }

    gslamAGIOModule1455PumpPower     OBJECT-TYPE
           SYNTAX      OCTET STRING(SIZE(1..8))
           MAX-ACCESS  read-only
           STATUS      current
           DESCRIPTION
                   " Kink Free Current Pump3 in DB"
           ::= { gslamAGIOModuleEntry 38 }

    gslamAGIOModuleTECCurrentPump1     OBJECT-TYPE
           SYNTAX      OCTET STRING(SIZE(1..8))
           MAX-ACCESS  read-only
           STATUS      current
           DESCRIPTION
                   "TEC Current for Pump Laser 1 "
           ::= { gslamAGIOModuleEntry 39 }

    gslamAGIOModuleTECCurrentPump2     OBJECT-TYPE
           SYNTAX      OCTET STRING(SIZE(1..8))
           MAX-ACCESS  read-only
           STATUS      current
           DESCRIPTION
                   "TEC Current for Pump Laser 2 "
           ::= { gslamAGIOModuleEntry 40 }

    gslamAGIOModuleTECCurrentPump3     OBJECT-TYPE
           SYNTAX      OCTET STRING(SIZE(1..8))
           MAX-ACCESS  read-only
           STATUS      current
           DESCRIPTION
                   "TEC Current for Pump Laser 3 "
           ::= { gslamAGIOModuleEntry 41 }

    gslamAGIOModulePump1SubmountTemp     OBJECT-TYPE
           SYNTAX      OCTET STRING(SIZE(1..8))
           MAX-ACCESS  read-only
           STATUS      current
           DESCRIPTION
                   " Pump 1 Submount Temperature "
           ::= { gslamAGIOModuleEntry 42 }

    gslamAGIOModulePump2SubmountTemp     OBJECT-TYPE
           SYNTAX      OCTET STRING(SIZE(1..8))
           MAX-ACCESS  read-only
           STATUS      current
           DESCRIPTION
                   " Pump 2 Submount Temperature "
           ::= { gslamAGIOModuleEntry 43}

    gslamAGIOModulePump3SubmountTemp     OBJECT-TYPE
           SYNTAX      OCTET STRING(SIZE(1..8))
           MAX-ACCESS  read-only
           STATUS      current
           DESCRIPTION
                   " Pump 3 Submount Temperature "
           ::= { gslamAGIOModuleEntry 44 }

	-- UV 5.0 CHANGE START

	-- IO module objects
	gslamAGREL50IOModuleTable		OBJECT-TYPE
		SYNTAX		SEQUENCE OF GslamAGREL50IOModuleEntry
		MAX-ACCESS	not-accessible
		STATUS		current
		DESCRIPTION
			"A table about the IO modules of GSLAM-AG."
	    ::= { ipiGslamAGIOModuleObjs 2 }

	gslamAGREL50IOModuleEntry OBJECT-TYPE
		SYNTAX  		GslamAGREL50IOModuleEntry
		MAX-ACCESS	not-accessible
		STATUS  		current
		DESCRIPTION
			"A row in module table.
			Entries can't be deleted or created via SNMP ops."
		INDEX   { gslamAGREL50ShelfIndex, gslamAGREL50IOModuleIndex }
	    ::= { gslamAGREL50IOModuleTable 1 }

	GslamAGREL50IOModuleEntry ::= SEQUENCE {
		gslamAGREL50IOModuleIndex			Unsigned32,
		gslamAGREL50IOModuleType			EquipmentTypeValue,
		gslamAGREL50IOModuleAction			ActionValue,
		gslamAGREL50IOModuleRowStatus		RowStatus,
		gslamAGREL50IOModuleLocation			LocationValue,
		gslamAGREL50IOModuleCLEI			CLEIValue,
		gslamAGREL50IOModulePrimaryState		PrimaryStateValue,
		gslamAGREL50IOModuleSecondaryState		SecondaryStateValue,
		gslamAGREL50IOModuleHWManufactureName	HWManufactureNameValue,
		gslamAGREL50IOModuleHWManufactureSerial	HWManufactureSerialValue,
		gslamAGREL50IOModuleHWRevision		HWRevisionValue,
		gslamAGREL50IOModuleHWManufacturePartName  HWPartNumberValue,
		gslamAGREL50IOModuleHWManufacturePartNumber HWPartNumberValue,
		gslamAGREL50IOModuleOperationalMode			ModuleOperationalModeValue,
		--gslamAGIOModuleAutoShutdown     FlagValue,
		gslamAGREL50IOROADMModuleOPLaserState		INTEGER,
		gslamAGREL50IOModuleDegreeId				Unsigned32,
		gslamAGREL50IOModuleGain					OCTET STRING,
		gslamAGREL50IOModulePump1ActualLBC		OCTET STRING,
		gslamAGREL50IOModulePump2ActualLBC		OCTET STRING,
		gslamAGREL50IOModulePump1KinkFreeCurrent	OCTET STRING,
		gslamAGREL50IOModulePump2KinkFreeCurrent	OCTET STRING,
		gslamAGREL50IOModuleOPSGroup1OPSMode		OPSModeValue,
		gslamAGREL50IOModuleOPSGroup1LOPMode		FlagValue,
		gslamAGREL50IOModuleOPSGroup2OPSMode		OPSModeValue,
		gslamAGREL50IOModuleOPSGroup2LOPMode		FlagValue,
		gslamAGREL50IOModuleFeatureCode			OCTET STRING,
		gslamAGREL50IOModuleFeatureKey			OCTET STRING,
		gslamAGREL50IOROADMModuleOCM1Degree    	Unsigned32,	
		gslamAGREL50IOROADMModuleOCM2Degree    	Unsigned32,	
		gslamAGREL50IOROADMModuleOCM3Degree    	Unsigned32,	
		gslamAGREL50IOROADMModuleOCM4Degree    	Unsigned32,
        gslamAGREL50IOROADMModuleDCFLossBorrowing   INTEGER,
        gslamAGREL50IOModuleFiberTiltCompensation   INTEGER,
        gslamAGREL50IOROADMModuleActualOPLaserState INTEGER,
        gslamAGREL50IOModuleDCMType                 CLEIValue, 
        gslamAGREL50IOModuleGainTCAThreshold      OCTET STRING,
        gslamAGREL50IOModuleLaserStatus           INTEGER,
        gslamAGREL50IOModulePump3ActualLBC        OCTET STRING,
        gslamAGREL50IOModulePump3KinkFreeCurrent  OCTET STRING,
        gslamAGREL50IOModule1425PumpPower         OCTET STRING,
        gslamAGREL50IOModule1455PumpPower         OCTET STRING,
        gslamAGREL50IOModuleTECCurrentPump1       OCTET STRING,
        gslamAGREL50IOModuleTECCurrentPump2       OCTET STRING,
        gslamAGREL50IOModuleTECCurrentPump3       OCTET STRING,
        gslamAGREL50IOModulePump1SubmountTemp     OCTET STRING,
        gslamAGREL50IOModulePump2SubmountTemp     OCTET STRING,
        gslamAGREL50IOModulePump3SubmountTemp     OCTET STRING
	}

	gslamAGREL50IOModuleIndex	OBJECT-TYPE
		SYNTAX		Unsigned32
		MAX-ACCESS	not-accessible
		STATUS		current
		DESCRIPTION
			"Index of GSLAM-AG IO module table. It uniquely identifies each module."
	    ::= { gslamAGREL50IOModuleEntry 1 }

	gslamAGREL50IOModuleType	OBJECT-TYPE
		SYNTAX EquipmentTypeValue
 	 	MAX-ACCESS  read-write
 	 	STATUS      current
 	 	DESCRIPTION
			"Indicates the equipment type of this IO module."
 	 	::= { gslamAGREL50IOModuleEntry 2 }

	gslamAGREL50IOModuleRowStatus		OBJECT-TYPE
		SYNTAX		RowStatus
		MAX-ACCESS	read-create
		STATUS		current
		DESCRIPTION
			"Current status of this GSLAM-AG IO module entry."
    	::= { gslamAGREL50IOModuleEntry 3 }

	gslamAGREL50IOModuleAction			OBJECT-TYPE
		SYNTAX		ActionValue
		MAX-ACCESS	read-write
		STATUS		current
		DESCRIPTION
			"Indicate command issued to this GSLAM-AG IO module."
	    ::= { gslamAGREL50IOModuleEntry 4 }

	gslamAGREL50IOModuleLocation		OBJECT-TYPE
		SYNTAX		LocationValue
		MAX-ACCESS	read-only
		STATUS		current
		DESCRIPTION
			"Indicate the location code of this GSLAM-AG IO module."
	    ::= { gslamAGREL50IOModuleEntry 5 }

	gslamAGREL50IOModuleCLEI		OBJECT-TYPE
		SYNTAX		CLEIValue
		MAX-ACCESS	read-write
		STATUS		current
		DESCRIPTION
			"Indicate the CLEI code of this GSLAM-AG IO module."
	    ::= { gslamAGREL50IOModuleEntry 6 }

	gslamAGREL50IOModulePrimaryState	OBJECT-TYPE
		SYNTAX	PrimaryStateValue
 	 	MAX-ACCESS  read-write
 	 	STATUS      current
 	 	DESCRIPTION
			"Indicates the primary state of this IO module."
 	 	::= { gslamAGREL50IOModuleEntry 7 }

	gslamAGREL50IOModuleSecondaryState	OBJECT-TYPE
		SYNTAX	SecondaryStateValue
 	 	MAX-ACCESS  read-only
 	 	STATUS      current
 	 	DESCRIPTION
			"Indicates the secondary state of this IO module."
 	 	::= { gslamAGREL50IOModuleEntry 8 }

	gslamAGREL50IOModuleHWManufactureName		OBJECT-TYPE
		SYNTAX		HWManufactureNameValue
		MAX-ACCESS	read-only
		STATUS		current
		DESCRIPTION
			"Indicate hardware manufacture name of this GSLAM-AG IO module."
	    ::= { gslamAGREL50IOModuleEntry 9 }

	gslamAGREL50IOModuleHWManufactureSerial		OBJECT-TYPE
		SYNTAX		HWManufactureSerialValue
		MAX-ACCESS	read-only
		STATUS		current
		DESCRIPTION
			"Indicate hardware manufacture serial number of this GSLAM-AG IO module."
	    ::= { gslamAGREL50IOModuleEntry 10 }

	gslamAGREL50IOModuleHWRevision		OBJECT-TYPE
		SYNTAX		HWRevisionValue
		MAX-ACCESS	read-only
		STATUS		current
		DESCRIPTION
			"Indicate hardware revision of this GSLAM-AG IO module."
	    ::= { gslamAGREL50IOModuleEntry 11 }

	gslamAGREL50IOModuleHWManufacturePartName	OBJECT-TYPE
		SYNTAX      HWPartNumberValue
		MAX-ACCESS  read-only
		STATUS      current
		DESCRIPTION
			"Indicate hardware manufacture part name about this
			GSLAM-AG IO module."
		::= { gslamAGREL50IOModuleEntry 12 }

	gslamAGREL50IOModuleHWManufacturePartNumber      OBJECT-TYPE
		SYNTAX      HWPartNumberValue
		MAX-ACCESS  read-only
		STATUS      current
		DESCRIPTION
			"Indicate hardware manufacture part number about this
			GSLAM-AG IO module."
		::= { gslamAGREL50IOModuleEntry 13 }

	gslamAGREL50IOModuleOperationalMode      OBJECT-TYPE
		SYNTAX      ModuleOperationalModeValue
		MAX-ACCESS  read-write
		STATUS      current
		DESCRIPTION
			"Defines module operational mode of GSLAM-AG IO module."
		::= { gslamAGREL50IOModuleEntry 14 }

	gslamAGREL50IOROADMModuleOPLaserState      OBJECT-TYPE
		SYNTAX      INTEGER {
			laser-state-not-present (0), --unsupport fiber type	
			laser-state-auto (1),
			laser-state-off (2),
			laser-state-on (3)
		}
		MAX-ACCESS  read-write
		STATUS      current
		DESCRIPTION
			"Indicates laser mode of Optical Amplifier upon
			 detection of input signal loss.This is replacing the autoshutdown flag"
		::= { gslamAGREL50IOModuleEntry 15 }

	gslamAGREL50IOModuleDegreeId      OBJECT-TYPE
		SYNTAX      Unsigned32
		MAX-ACCESS  read-write
		STATUS      current
		DESCRIPTION
			"Indicates association of a Optical module with a degree."
		::= { gslamAGREL50IOModuleEntry 16 }

	gslamAGREL50IOModuleGain      OBJECT-TYPE
		SYNTAX      OCTET STRING(SIZE(1..8))
		MAX-ACCESS  read-write
		STATUS      current
		DESCRIPTION
			"Defines Optical gain (or module level gain,Gtotal) for a variable gain optical amplifier"
		::= { gslamAGREL50IOModuleEntry 17 }

	gslamAGREL50IOModulePump1ActualLBC      OBJECT-TYPE
		SYNTAX      OCTET STRING(SIZE(1..8))
		MAX-ACCESS  read-only
		STATUS      current
		DESCRIPTION
			"Laser pump 1 actual LBC value in DB"
		::= { gslamAGREL50IOModuleEntry 18 }

	gslamAGREL50IOModulePump2ActualLBC      OBJECT-TYPE
		SYNTAX      OCTET STRING(SIZE(1..8))
		MAX-ACCESS  read-only
		STATUS      current
		DESCRIPTION
			"Laser pump 2 actual LBC value in DB"
		::= { gslamAGREL50IOModuleEntry 19 }

	gslamAGREL50IOModulePump1KinkFreeCurrent      OBJECT-TYPE
		SYNTAX      OCTET STRING(SIZE(1..8))
		MAX-ACCESS  read-only
		STATUS      current
		DESCRIPTION
			"Laser pump 1 monitored LBC value in DB"
		::= { gslamAGREL50IOModuleEntry 20 }

	gslamAGREL50IOModulePump2KinkFreeCurrent      OBJECT-TYPE
		SYNTAX      OCTET STRING(SIZE(1..8))
		MAX-ACCESS  read-only
		STATUS      current
		DESCRIPTION
			"Laser pump 2 monitored LBC value in DB"
		::= { gslamAGREL50IOModuleEntry 21 }

	gslamAGREL50IOModuleOPSGroup1OPSMode      OBJECT-TYPE
		SYNTAX      OPSModeValue
		MAX-ACCESS  read-write
		STATUS      current
		DESCRIPTION
			"OPS mode of OPS group 1"
		::= { gslamAGREL50IOModuleEntry 22 }

	gslamAGREL50IOModuleOPSGroup1LOPMode      OBJECT-TYPE
		SYNTAX      FlagValue
		MAX-ACCESS  read-write
		STATUS      current
		DESCRIPTION
			"Loss of power mode for OPS group 1"
		::= { gslamAGREL50IOModuleEntry 23 }

	gslamAGREL50IOModuleOPSGroup2OPSMode      OBJECT-TYPE
		SYNTAX      OPSModeValue
		MAX-ACCESS  read-write
		STATUS      current
		DESCRIPTION
			"OPS mode of OPS group 2"
		::= { gslamAGREL50IOModuleEntry 24 }

	gslamAGREL50IOModuleOPSGroup2LOPMode      OBJECT-TYPE
		SYNTAX      FlagValue
		MAX-ACCESS  read-write
		STATUS      current
		DESCRIPTION
			"Loss of power mode for OPS group 2"
		::= { gslamAGREL50IOModuleEntry 25 }

	gslamAGREL50IOModuleFeatureCode     OBJECT-TYPE
       		SYNTAX      OCTET STRING(SIZE(0..40))
       		MAX-ACCESS  read-write
       		STATUS      current
       		DESCRIPTION
				"Indicates a code for specific set of services in CN4200 shelf."
 	 	::= { gslamAGREL50IOModuleEntry 26 }

	gslamAGREL50IOModuleFeatureKey     OBJECT-TYPE
       		SYNTAX      OCTET STRING(SIZE(0..40))
       		MAX-ACCESS  read-write
       		STATUS      current
       		DESCRIPTION
				"A key to enable specific set of services in CN4200 shelf.
				This is write only parameter at module level"
 	 	::= { gslamAGREL50IOModuleEntry 27 }

	gslamAGREL50IOROADMModuleOCM1Degree     OBJECT-TYPE
            SYNTAX      Unsigned32
            MAX-ACCESS  read-write
            STATUS      current
            DESCRIPTION
                "1st Deree of the OCM module"
        ::= { gslamAGREL50IOModuleEntry 28 }

	gslamAGREL50IOROADMModuleOCM2Degree     OBJECT-TYPE
            SYNTAX      Unsigned32
            MAX-ACCESS  read-write
            STATUS      current
            DESCRIPTION
                "1st Deree of the OCM module"
        ::= { gslamAGREL50IOModuleEntry 29 }

	gslamAGREL50IOROADMModuleOCM3Degree     OBJECT-TYPE
            SYNTAX      Unsigned32
            MAX-ACCESS  read-write
            STATUS      current
            DESCRIPTION
                "1st Deree of the OCM module"
        ::= { gslamAGREL50IOModuleEntry 30 }

	gslamAGREL50IOROADMModuleOCM4Degree     OBJECT-TYPE
            SYNTAX      Unsigned32
            MAX-ACCESS  read-write
            STATUS      current
            DESCRIPTION
                "1st Deree of the OCM module"
        ::= { gslamAGREL50IOModuleEntry 31 }

    gslamAGREL50IOROADMModuleDCFLossBorrowing     OBJECT-TYPE
        SYNTAX INTEGER {
             unknown(1),
             enabled(2),
             disabled(3)
        }
        MAX-ACCESS      read-write
        STATUS    current
        DESCRIPTION
            "Indicates if module loss borrowing is enabled or disabled. 
             Default Value is DISABLED for OAV-VS-U-CP"
        ::= { gslamAGREL50IOModuleEntry 32 }

    gslamAGREL50IOModuleFiberTiltCompensation OBJECT-TYPE
        SYNTAX      INTEGER {
            unknown (1),
            enabled (2),
            disabled (3)
        }

        MAX-ACCESS  read-write
        STATUS      current
        DESCRIPTION
            "Fiber Tilt compensation provisioning in UV system. 
             Default depends on module type."
        ::= { gslamAGREL50IOModuleEntry 33}

    gslamAGREL50IOROADMModuleActualOPLaserState OBJECT-TYPE
        SYNTAX      INTEGER {
            laser-state-not-present (0),  
            laser-state-on (1),
            laser-state-off (2)
        }
        MAX-ACCESS read-only
        STATUS      current
        DESCRIPTION
            "Indicates actual OA laser mode of CN4200 Optical Amplifier."
        ::= { gslamAGREL50IOModuleEntry 34 }

    gslamAGREL50IOModuleDCMType     OBJECT-TYPE
        SYNTAX      CLEIValue
        MAX-ACCESS  read-write
        STATUS      current
        DESCRIPTION
            "Indicate the CLEI code of DCM."
        ::= { gslamAGREL50IOModuleEntry 35 }

    gslamAGREL50IOModuleGainTCAThreshold     OBJECT-TYPE
        SYNTAX  OCTET STRING(SIZE(1..8))
        MAX-ACCESS      read-write
        STATUS    current
        DESCRIPTION
            "Gain TCA value for Raman module in dB "
        ::= { gslamAGREL50IOModuleEntry 36 }

    gslamAGREL50IOModuleLaserStatus     OBJECT-TYPE
        SYNTAX  INTEGER {
             not-applicable(1),
             off(2),
             on(3)
        }
        MAX-ACCESS      read-only
        STATUS    current
        DESCRIPTION
            "Indicates if the laser is on or off for an amplifier"
        ::= { gslamAGREL50IOModuleEntry 37 }

    gslamAGREL50IOModulePump3ActualLBC      OBJECT-TYPE
           SYNTAX      OCTET STRING(SIZE(1..8))
           MAX-ACCESS  read-only
           STATUS      current
           DESCRIPTION
                   "Laser pump 3 actual LBC value in DB"
           ::= { gslamAGREL50IOModuleEntry 38 }

    gslamAGREL50IOModulePump3KinkFreeCurrent      OBJECT-TYPE
           SYNTAX      OCTET STRING(SIZE(1..8))
           MAX-ACCESS  read-only
           STATUS      current
           DESCRIPTION
                   " Kink Free Current Pump3 in DB"
           ::= { gslamAGREL50IOModuleEntry 39 }

    gslamAGREL50IOModule1425PumpPower      OBJECT-TYPE
           SYNTAX      OCTET STRING(SIZE(1..8))
           MAX-ACCESS  read-only
           STATUS      current
           DESCRIPTION
                   " 1425nm Pump Power  in DB"
           ::= { gslamAGREL50IOModuleEntry 40 }

    gslamAGREL50IOModule1455PumpPower     OBJECT-TYPE
           SYNTAX      OCTET STRING(SIZE(1..8))
           MAX-ACCESS  read-only
           STATUS      current
           DESCRIPTION
                   " Kink Free Current Pump3 in DB"
           ::= { gslamAGREL50IOModuleEntry 41 }
    
    gslamAGREL50IOModuleTECCurrentPump1     OBJECT-TYPE
           SYNTAX      OCTET STRING(SIZE(1..8))
           MAX-ACCESS  read-only
           STATUS      current
           DESCRIPTION
                   "TEC Current for Pump Laser 1 "
           ::= { gslamAGREL50IOModuleEntry 42 }
    
    gslamAGREL50IOModuleTECCurrentPump2     OBJECT-TYPE
           SYNTAX      OCTET STRING(SIZE(1..8))
           MAX-ACCESS  read-only
           STATUS      current
           DESCRIPTION
                   "TEC Current for Pump Laser 2 "
           ::= { gslamAGREL50IOModuleEntry 43 }
    
    gslamAGREL50IOModuleTECCurrentPump3     OBJECT-TYPE
           SYNTAX      OCTET STRING(SIZE(1..8))
           MAX-ACCESS  read-only
           STATUS      current
           DESCRIPTION
                   "TEC Current for Pump Laser 3 "
           ::= { gslamAGREL50IOModuleEntry 44 }

    gslamAGREL50IOModulePump1SubmountTemp     OBJECT-TYPE
           SYNTAX      OCTET STRING(SIZE(1..8))
           MAX-ACCESS  read-only
           STATUS      current
           DESCRIPTION
                   " Pump 1 Submount Temperature "
           ::= { gslamAGREL50IOModuleEntry 45 }

    gslamAGREL50IOModulePump2SubmountTemp     OBJECT-TYPE
           SYNTAX      OCTET STRING(SIZE(1..8))
           MAX-ACCESS  read-only
           STATUS      current
           DESCRIPTION
                   " Pump 2 Submount Temperature "
           ::= { gslamAGREL50IOModuleEntry 46}

    gslamAGREL50IOModulePump3SubmountTemp     OBJECT-TYPE
           SYNTAX      OCTET STRING(SIZE(1..8))
           MAX-ACCESS  read-only
           STATUS      current
           DESCRIPTION
                   " Pump 3 Submount Temperature "
           ::= { gslamAGREL50IOModuleEntry 47 }

	-- UV 5.0 CHANGE START
	-- VOA table
	gslamAGREL50IOModuleVoaTable		OBJECT-TYPE
		SYNTAX		SEQUENCE OF GslamAGREL50IOModuleVoaEntry
		MAX-ACCESS	not-accessible
		STATUS		current
		DESCRIPTION
			"A table about the IO modules of GSLAM-AG."
	    ::= { ipiGslamAGIOModuleObjs 3 }

	gslamAGREL50IOModuleVoaEntry OBJECT-TYPE
		SYNTAX  		GslamAGREL50IOModuleVoaEntry
		MAX-ACCESS	not-accessible
		STATUS  		current
		DESCRIPTION
			"A row in module table.
			Entries can't be deleted or created via SNMP ops."
		INDEX   { gslamAGREL50ShelfIndex, gslamAGREL50IOModuleIndex,
					gslamAGREL50IOModuleVoaIndex }
	    ::= { gslamAGREL50IOModuleVoaTable 1 }

	GslamAGREL50IOModuleVoaEntry ::= SEQUENCE {
		gslamAGREL50IOModuleVoaIndex			Unsigned32,
		gslamAGREL50IOModuleVoaRowStatus		RowStatus,
		gslamAGREL50IOModuleVoaAttenuation	OCTET STRING
	}

	gslamAGREL50IOModuleVoaIndex     OBJECT-TYPE
            SYNTAX      Unsigned32
            MAX-ACCESS  read-write
            STATUS      current
            DESCRIPTION
                "Index of the VOA table. This maps right into the enum
					_IPIMgmtVmuxVoaType or _IPIMgmtDwrVoaType"
        ::= { gslamAGREL50IOModuleVoaEntry 1 }

	gslamAGREL50IOModuleVoaRowStatus     OBJECT-TYPE
            SYNTAX      RowStatus
            MAX-ACCESS  read-write
            STATUS      current
            DESCRIPTION
                "Rowstatus value for this table"
        ::= { gslamAGREL50IOModuleVoaEntry 2 }

	gslamAGREL50IOModuleVoaAttenuation	OBJECT-TYPE
		SYNTAX      OCTET STRING(SIZE(1..20))
		MAX-ACCESS  read-write
		STATUS      current
		DESCRIPTION
			"Indicates the VOA attenuation val for a DWR or VMUX module"
		::= {gslamAGREL50IOModuleVoaEntry 3 }


	-- UV 5.0 CHANGE END

	-- power module objects
	gslamAGPwrModuleTable		OBJECT-TYPE
		SYNTAX		SEQUENCE OF GslamAGPwrModuleEntry
		MAX-ACCESS	not-accessible
		STATUS		current
		DESCRIPTION
			"A table about the power modules of GSLAM-AG."
	    ::= { ipiGslamAGPwrModuleObjs 1 }

	gslamAGPwrModuleEntry OBJECT-TYPE
		SYNTAX  		GslamAGPwrModuleEntry
		MAX-ACCESS	not-accessible
		STATUS  		current
		DESCRIPTION
			"A row in power module table.
			Entries can't be deleted or created via SNMP ops."
		INDEX   { gslamAGShelfIndex, gslamAGPwrModuleIndex }
	    ::= { gslamAGPwrModuleTable 1 }

	GslamAGPwrModuleEntry ::= SEQUENCE {
		gslamAGPwrModuleIndex	Unsigned32,
		gslamAGPwrModuleType		EquipmentTypeValue,
		gslamAGPwrModuleLocation	LocationValue,
		gslamAGPwrModuleCLEI		CLEIValue,
		gslamAGPwrModulePrimaryState				PrimaryStateValue,
		gslamAGPwrModuleSecondaryState			SecondaryStateValue,
		gslamAGPwrModuleHWManufactureName		HWManufactureNameValue,
		gslamAGPwrModuleHWManufactureSerial	HWManufactureSerialValue,
		gslamAGPwrModuleHWRevision				HWRevisionValue,
		gslamAGPwrModuleHWManufacturePartName  HWPartNumberValue,
		gslamAGPwrModuleHWManufacturePartNumber	HWPartNumberValue
	}

	gslamAGPwrModuleIndex	OBJECT-TYPE
		SYNTAX		Unsigned32
		MAX-ACCESS	not-accessible
		STATUS		current
		DESCRIPTION
			"Index of GSLAM-AG Pwr module table. It uniquely identifies each module."
	    ::= { gslamAGPwrModuleEntry 1 }

	gslamAGPwrModuleType	OBJECT-TYPE
		SYNTAX EquipmentTypeValue
 	 	MAX-ACCESS  read-only
 	 	STATUS      current
 	 	DESCRIPTION
			"Indicates the equipment type of this GSLAM-AG power module."
 	 	::= { gslamAGPwrModuleEntry 2 }

	gslamAGPwrModuleLocation		OBJECT-TYPE
		SYNTAX		LocationValue
		MAX-ACCESS	read-only
		STATUS		current
		DESCRIPTION
			"Indicate the location code of this GSLAM-AG power module."
	    ::= { gslamAGPwrModuleEntry 3 }

	gslamAGPwrModuleCLEI		OBJECT-TYPE
		SYNTAX		CLEIValue
		MAX-ACCESS	read-only
		STATUS		current
		DESCRIPTION
			"Indicate the CLEI code of this GSLAM-AG power module."
	    ::= { gslamAGPwrModuleEntry 4 }

	gslamAGPwrModulePrimaryState	OBJECT-TYPE
		SYNTAX	PrimaryStateValue
 	 	MAX-ACCESS  read-only
 	 	STATUS      current
 	 	DESCRIPTION
			"Indicates the primary state of this GSLAM-AG power module."
 	 	::= { gslamAGPwrModuleEntry 5 }

	gslamAGPwrModuleSecondaryState	OBJECT-TYPE
		SYNTAX	SecondaryStateValue
 	 	MAX-ACCESS  read-only
 	 	STATUS      current
 	 	DESCRIPTION
			"Indicates the secondary state of this GSLAM-AG power module."
 	 	::= { gslamAGPwrModuleEntry 6 }

 	 gslamAGPwrModuleHWManufactureName		OBJECT-TYPE
		SYNTAX		HWManufactureNameValue
		MAX-ACCESS	read-only
		STATUS		current
		DESCRIPTION
			"Indicate hardware manufacture name of this GSLAM-AG power module."
	    ::= { gslamAGPwrModuleEntry 7 }

	gslamAGPwrModuleHWManufactureSerial		OBJECT-TYPE
		SYNTAX		HWManufactureSerialValue
		MAX-ACCESS	read-only
		STATUS		current
		DESCRIPTION
			"Indicate hardware manufacture serial number of this GSLAM-AG power module."
	    ::= { gslamAGPwrModuleEntry 8 }

	gslamAGPwrModuleHWRevision		OBJECT-TYPE
		SYNTAX		HWRevisionValue
		MAX-ACCESS	read-only
		STATUS		current
		DESCRIPTION
			"Indicate hardware revision of this GSLAM-AG power module."
	    ::= { gslamAGPwrModuleEntry 9 }

	gslamAGPwrModuleHWManufacturePartName	OBJECT-TYPE
		SYNTAX      HWPartNumberValue
		MAX-ACCESS  read-only
		STATUS      current
		DESCRIPTION
			"Indicate hardware manufacture part name about this
			GSLAM-AG power module."
	    ::= { gslamAGPwrModuleEntry 10 }

	gslamAGPwrModuleHWManufacturePartNumber      OBJECT-TYPE
		SYNTAX      HWPartNumberValue
		MAX-ACCESS  read-only
		STATUS      current
		DESCRIPTION
			"Indicate hardware manufacture part number about this
			GSLAM-AG power module."
	    ::= { gslamAGPwrModuleEntry 11 }

	-- UV 5.0 START

	-- power module objects
	gslamAGREL50PwrModuleTable		OBJECT-TYPE
		SYNTAX		SEQUENCE OF GslamAGREL50PwrModuleEntry
		MAX-ACCESS	not-accessible
		STATUS		current
		DESCRIPTION
			"A table about the power modules of GSLAM-AG."
	    ::= { ipiGslamAGPwrModuleObjs 2 }

	gslamAGREL50PwrModuleEntry OBJECT-TYPE
		SYNTAX  		GslamAGREL50PwrModuleEntry
		MAX-ACCESS	not-accessible
		STATUS  		current
		DESCRIPTION
			"A row in power module table.
			Entries can't be deleted or created via SNMP ops."
		INDEX   { gslamAGREL50ShelfIndex, gslamAGREL50PwrModuleIndex }
	    ::= { gslamAGREL50PwrModuleTable 1 }

	GslamAGREL50PwrModuleEntry ::= SEQUENCE {
		gslamAGREL50PwrModuleIndex	Unsigned32,
		gslamAGREL50PwrModuleType		EquipmentTypeValue,
		gslamAGREL50PwrModuleLocation	LocationValue,
		gslamAGREL50PwrModuleCLEI		CLEIValue,
		gslamAGREL50PwrModulePrimaryState				PrimaryStateValue,
		gslamAGREL50PwrModuleSecondaryState			SecondaryStateValue,
		gslamAGREL50PwrModuleHWManufactureName		HWManufactureNameValue,
		gslamAGREL50PwrModuleHWManufactureSerial	HWManufactureSerialValue,
		gslamAGREL50PwrModuleHWRevision				HWRevisionValue,
		gslamAGREL50PwrModuleHWManufacturePartName  HWPartNumberValue,
		gslamAGREL50PwrModuleHWManufacturePartNumber	HWPartNumberValue
	}

	gslamAGREL50PwrModuleIndex	OBJECT-TYPE
		SYNTAX		Unsigned32
		MAX-ACCESS	not-accessible
		STATUS		current
		DESCRIPTION
			"Index of GSLAM-AG Pwr module table. It uniquely identifies each module."
	    ::= { gslamAGREL50PwrModuleEntry 1 }

	gslamAGREL50PwrModuleType	OBJECT-TYPE
		SYNTAX EquipmentTypeValue
 	 	MAX-ACCESS  read-only
 	 	STATUS      current
 	 	DESCRIPTION
			"Indicates the equipment type of this GSLAM-AG power module."
 	 	::= { gslamAGREL50PwrModuleEntry 2 }

	gslamAGREL50PwrModuleLocation		OBJECT-TYPE
		SYNTAX		LocationValue
		MAX-ACCESS	read-only
		STATUS		current
		DESCRIPTION
			"Indicate the location code of this GSLAM-AG power module."
	    ::= { gslamAGREL50PwrModuleEntry 3 }

	gslamAGREL50PwrModuleCLEI		OBJECT-TYPE
		SYNTAX		CLEIValue
		MAX-ACCESS	read-only
		STATUS		current
		DESCRIPTION
			"Indicate the CLEI code of this GSLAM-AG power module."
	    ::= { gslamAGREL50PwrModuleEntry 4 }

	gslamAGREL50PwrModulePrimaryState	OBJECT-TYPE
		SYNTAX	PrimaryStateValue
 	 	MAX-ACCESS  read-only
 	 	STATUS      current
 	 	DESCRIPTION
			"Indicates the primary state of this GSLAM-AG power module."
 	 	::= { gslamAGREL50PwrModuleEntry 5 }

	gslamAGREL50PwrModuleSecondaryState	OBJECT-TYPE
		SYNTAX	SecondaryStateValue
 	 	MAX-ACCESS  read-only
 	 	STATUS      current
 	 	DESCRIPTION
			"Indicates the secondary state of this GSLAM-AG power module."
 	 	::= { gslamAGREL50PwrModuleEntry 6 }

 	 gslamAGREL50PwrModuleHWManufactureName		OBJECT-TYPE
		SYNTAX		HWManufactureNameValue
		MAX-ACCESS	read-only
		STATUS		current
		DESCRIPTION
			"Indicate hardware manufacture name of this GSLAM-AG power module."
	    ::= { gslamAGREL50PwrModuleEntry 7 }

	gslamAGREL50PwrModuleHWManufactureSerial		OBJECT-TYPE
		SYNTAX		HWManufactureSerialValue
		MAX-ACCESS	read-only
		STATUS		current
		DESCRIPTION
			"Indicate hardware manufacture serial number of this GSLAM-AG power module."
	    ::= { gslamAGREL50PwrModuleEntry 8 }

	gslamAGREL50PwrModuleHWRevision		OBJECT-TYPE
		SYNTAX		HWRevisionValue
		MAX-ACCESS	read-only
		STATUS		current
		DESCRIPTION
			"Indicate hardware revision of this GSLAM-AG power module."
	    ::= { gslamAGREL50PwrModuleEntry 9 }

	gslamAGREL50PwrModuleHWManufacturePartName	OBJECT-TYPE
		SYNTAX      HWPartNumberValue
		MAX-ACCESS  read-only
		STATUS      current
		DESCRIPTION
			"Indicate hardware manufacture part name about this
			GSLAM-AG power module."
	    ::= { gslamAGREL50PwrModuleEntry 10 }

	gslamAGREL50PwrModuleHWManufacturePartNumber      OBJECT-TYPE
		SYNTAX      HWPartNumberValue
		MAX-ACCESS  read-only
		STATUS      current
		DESCRIPTION
			"Indicate hardware manufacture part number about this
			GSLAM-AG power module."
	    ::= { gslamAGREL50PwrModuleEntry 11 }

	-- fan tray objects
	gslamAGFanModuleTable		OBJECT-TYPE
		SYNTAX		SEQUENCE OF GslamAGFanModuleEntry
		MAX-ACCESS	not-accessible
		STATUS		current
		DESCRIPTION
			"A table about the fan trays of GSLAM-AG."
	    ::= { ipiGslamAGFanModuleObjs 1 }

	gslamAGFanModuleEntry OBJECT-TYPE
		SYNTAX  		GslamAGFanModuleEntry
		MAX-ACCESS	not-accessible
		STATUS  		current
		DESCRIPTION
			"A row in fan tray table.
			Entries can't be deleted or created via SNMP ops."
		INDEX   { gslamAGShelfIndex, gslamAGFanModuleIndex }
	    ::= { gslamAGFanModuleTable 1}

	GslamAGFanModuleEntry ::= SEQUENCE {
		gslamAGFanModuleIndex		Unsigned32,
		gslamAGFanModuleType		EquipmentTypeValue,
		gslamAGFanModuleLocation	LocationValue,
		gslamAGFanModuleCLEI		CLEIValue,
		gslamAGFanModulePrimaryState			PrimaryStateValue,
		gslamAGFanModuleSecondaryState			SecondaryStateValue,
		gslamAGFanModuleHWManufactureName		HWManufactureNameValue,
		gslamAGFanModuleHWManufactureSerial	HWManufactureSerialValue,
		gslamAGFanModuleHWRevision		HWRevisionValue,
		gslamAGFanModuleHWManufacturePartName   HWPartNumberValue,
		gslamAGFanModuleHWManufacturePartNumber  HWPartNumberValue
	}

	gslamAGFanModuleIndex	OBJECT-TYPE
		SYNTAX		Unsigned32
		MAX-ACCESS	not-accessible
		STATUS		current
		DESCRIPTION
			"Index of GSLAM-AG fan tray table. It uniquely identifies
			 each fan tray within a shelf."
	    ::= { gslamAGFanModuleEntry 1 }

	gslamAGFanModuleType	OBJECT-TYPE
		SYNTAX EquipmentTypeValue
 	 	MAX-ACCESS  read-only
 	 	STATUS      current
 	 	DESCRIPTION
			"Indicates the equipment type of this GSLAM-AG fan tray."
 	 	::= { gslamAGFanModuleEntry 2 }

	gslamAGFanModuleLocation		OBJECT-TYPE
		SYNTAX		LocationValue
		MAX-ACCESS	read-only
		STATUS		current
		DESCRIPTION
			"Indicate the location code of this GSLAM-AG fan tray."
	    ::= { gslamAGFanModuleEntry 3 }

	gslamAGFanModuleCLEI		OBJECT-TYPE
		SYNTAX		CLEIValue
		MAX-ACCESS	read-only
		STATUS		current
		DESCRIPTION
			"Indicate the CLEI code of this GSLAM-AG fan tray."
	    ::= { gslamAGFanModuleEntry 4 }

	gslamAGFanModulePrimaryState	OBJECT-TYPE
		SYNTAX	PrimaryStateValue
 	 	MAX-ACCESS  read-only
 	 	STATUS      current
 	 	DESCRIPTION
			"Indicates the primary state of this GSLAM-AG fan tray."
 	 	::= { gslamAGFanModuleEntry 5 }

	gslamAGFanModuleSecondaryState	OBJECT-TYPE
		SYNTAX	SecondaryStateValue
 	 	MAX-ACCESS  read-only
 	 	STATUS      current
 	 	DESCRIPTION
			"Indicates the secondary state of this GSLAM-AG fan tray."
 	 	::= { gslamAGFanModuleEntry 6 }

	gslamAGFanModuleHWManufactureName		OBJECT-TYPE
		SYNTAX		HWManufactureNameValue
		MAX-ACCESS	read-only
		STATUS		current
		DESCRIPTION
			"Indicate hardware manufacture name of this GSLAM-AG fan tray."
	::= { gslamAGFanModuleEntry 7 }

	gslamAGFanModuleHWManufactureSerial		OBJECT-TYPE
		SYNTAX		HWManufactureSerialValue
		MAX-ACCESS	read-only
		STATUS		current
		DESCRIPTION
			"Indicate hardware manufacture serial number of this GSLAM-AG fan tray."
	    ::= { gslamAGFanModuleEntry 8 }

	gslamAGFanModuleHWRevision		OBJECT-TYPE
		SYNTAX		HWRevisionValue
		MAX-ACCESS	read-only
		STATUS		current
		DESCRIPTION
			"Indicate hardware revision of this GSLAM-AG fan tray."
	    ::= { gslamAGFanModuleEntry 9 }

	gslamAGFanModuleHWManufacturePartName	OBJECT-TYPE
		SYNTAX      HWPartNumberValue
		MAX-ACCESS  read-only
		STATUS      current
		DESCRIPTION
			"Indicate hardware manufacture part name of this
			GSLAM-AG fan tray."
	    ::= { gslamAGFanModuleEntry 10 }

	gslamAGFanModuleHWManufacturePartNumber      OBJECT-TYPE
		SYNTAX      HWPartNumberValue
		MAX-ACCESS  read-only
		STATUS      current
		DESCRIPTION
			"Indicate hardware manufacture part number about this
			GSLAM-AG power module."
	    ::= { gslamAGFanModuleEntry 11 }

	--UV 5.0  START

	-- fan tray objects
	gslamAGREL50FanModuleTable		OBJECT-TYPE
		SYNTAX		SEQUENCE OF GslamAGREL50FanModuleEntry
		MAX-ACCESS	not-accessible
		STATUS		current
		DESCRIPTION
			"A table about the fan trays of GSLAM-AG."
	    ::= { ipiGslamAGFanModuleObjs 2 }

	gslamAGREL50FanModuleEntry OBJECT-TYPE
		SYNTAX  		GslamAGREL50FanModuleEntry
		MAX-ACCESS	not-accessible
		STATUS  		current
		DESCRIPTION
			"A row in fan tray table.
			Entries can't be deleted or created via SNMP ops."
		INDEX   { gslamAGREL50ShelfIndex, gslamAGREL50FanModuleIndex }
	    ::= { gslamAGREL50FanModuleTable 1}

	GslamAGREL50FanModuleEntry ::= SEQUENCE {
		gslamAGREL50FanModuleIndex		Unsigned32,
		gslamAGREL50FanModuleType		EquipmentTypeValue,
		gslamAGREL50FanModuleLocation	LocationValue,
		gslamAGREL50FanModuleCLEI		CLEIValue,
		gslamAGREL50FanModulePrimaryState			PrimaryStateValue,
		gslamAGREL50FanModuleSecondaryState			SecondaryStateValue,
		gslamAGREL50FanModuleHWManufactureName		HWManufactureNameValue,
		gslamAGREL50FanModuleHWManufactureSerial	HWManufactureSerialValue,
		gslamAGREL50FanModuleHWRevision		HWRevisionValue,
		gslamAGREL50FanModuleHWManufacturePartName   HWPartNumberValue,
		gslamAGREL50FanModuleHWManufacturePartNumber  HWPartNumberValue
	}

	gslamAGREL50FanModuleIndex	OBJECT-TYPE
		SYNTAX		Unsigned32
		MAX-ACCESS	not-accessible
		STATUS		current
		DESCRIPTION
			"Index of GSLAM-AG fan tray table. It uniquely identifies
			 each fan tray within a shelf."
	    ::= { gslamAGREL50FanModuleEntry 1 }

	gslamAGREL50FanModuleType	OBJECT-TYPE
		SYNTAX EquipmentTypeValue
 	 	MAX-ACCESS  read-only
 	 	STATUS      current
 	 	DESCRIPTION
			"Indicates the equipment type of this GSLAM-AG fan tray."
 	 	::= { gslamAGREL50FanModuleEntry 2 }

	gslamAGREL50FanModuleLocation		OBJECT-TYPE
		SYNTAX		LocationValue
		MAX-ACCESS	read-only
		STATUS		current
		DESCRIPTION
			"Indicate the location code of this GSLAM-AG fan tray."
	    ::= { gslamAGREL50FanModuleEntry 3 }

	gslamAGREL50FanModuleCLEI		OBJECT-TYPE
		SYNTAX		CLEIValue
		MAX-ACCESS	read-only
		STATUS		current
		DESCRIPTION
			"Indicate the CLEI code of this GSLAM-AG fan tray."
	    ::= { gslamAGREL50FanModuleEntry 4 }

	gslamAGREL50FanModulePrimaryState	OBJECT-TYPE
		SYNTAX	PrimaryStateValue
 	 	MAX-ACCESS  read-only
 	 	STATUS      current
 	 	DESCRIPTION
			"Indicates the primary state of this GSLAM-AG fan tray."
 	 	::= { gslamAGREL50FanModuleEntry 5 }

	gslamAGREL50FanModuleSecondaryState	OBJECT-TYPE
		SYNTAX	SecondaryStateValue
 	 	MAX-ACCESS  read-only
 	 	STATUS      current
 	 	DESCRIPTION
			"Indicates the secondary state of this GSLAM-AG fan tray."
 	 	::= { gslamAGREL50FanModuleEntry 6 }

	gslamAGREL50FanModuleHWManufactureName		OBJECT-TYPE
		SYNTAX		HWManufactureNameValue
		MAX-ACCESS	read-only
		STATUS		current
		DESCRIPTION
			"Indicate hardware manufacture name of this GSLAM-AG fan tray."
	::= { gslamAGREL50FanModuleEntry 7 }

	gslamAGREL50FanModuleHWManufactureSerial		OBJECT-TYPE
		SYNTAX		HWManufactureSerialValue
		MAX-ACCESS	read-only
		STATUS		current
		DESCRIPTION
			"Indicate hardware manufacture serial number of this GSLAM-AG fan tray."
	    ::= { gslamAGREL50FanModuleEntry 8 }

	gslamAGREL50FanModuleHWRevision		OBJECT-TYPE
		SYNTAX		HWRevisionValue
		MAX-ACCESS	read-only
		STATUS		current
		DESCRIPTION
			"Indicate hardware revision of this GSLAM-AG fan tray."
	    ::= { gslamAGREL50FanModuleEntry 9 }

	gslamAGREL50FanModuleHWManufacturePartName	OBJECT-TYPE
		SYNTAX      HWPartNumberValue
		MAX-ACCESS  read-only
		STATUS      current
		DESCRIPTION
			"Indicate hardware manufacture part name of this
			GSLAM-AG fan tray."
	    ::= { gslamAGREL50FanModuleEntry 10 }

	gslamAGREL50FanModuleHWManufacturePartNumber      OBJECT-TYPE
		SYNTAX      HWPartNumberValue
		MAX-ACCESS  read-only
		STATUS      current
		DESCRIPTION
			"Indicate hardware manufacture part number about this
			GSLAM-AG power module."
	    ::= { gslamAGREL50FanModuleEntry 11 }

	--UV 5.0 END

	-- alarm module objects
	gslamAGAlarmModuleTable		OBJECT-TYPE
		SYNTAX		SEQUENCE OF GslamAGAlarmModuleEntry
		MAX-ACCESS	not-accessible
		STATUS		current
		DESCRIPTION
			"A table about the alarm modules of GSLAM-AG."
	    ::= { ipiGslamAGAlarmModuleObjs 1 }

	gslamAGAlarmModuleEntry OBJECT-TYPE
		SYNTAX  		GslamAGAlarmModuleEntry
		MAX-ACCESS	not-accessible
		STATUS  		current
		DESCRIPTION
			"A row in alarm module table.
			Entries can't be deleted or created via SNMP ops."
		INDEX   { gslamAGShelfIndex, gslamAGAlarmModuleIndex }
	    ::= { gslamAGAlarmModuleTable 1 }

	GslamAGAlarmModuleEntry ::= SEQUENCE {
		gslamAGAlarmModuleIndex	Unsigned32,
		gslamAGAlarmModuleType		EquipmentTypeValue,
		gslamAGAlarmModuleLocation	LocationValue,
		gslamAGAlarmModuleCLEI		CLEIValue,
		gslamAGAlarmModulePrimaryState				PrimaryStateValue,
		gslamAGAlarmModuleSecondaryState			SecondaryStateValue,
		gslamAGAlarmModuleHWManufactureName		HWManufactureNameValue,
		gslamAGAlarmModuleHWManufactureSerial	HWManufactureSerialValue,
		gslamAGAlarmModuleHWRevision				HWRevisionValue,
		gslamAGAlarmModuleHWManufacturePartName  HWPartNumberValue,
		gslamAGAlarmModuleHWManufacturePartNumber	HWPartNumberValue
	}

	gslamAGAlarmModuleIndex	OBJECT-TYPE
		SYNTAX		Unsigned32
		MAX-ACCESS	not-accessible
		STATUS		current
		DESCRIPTION
			"Index of GSLAM-AG Alarm module table. It uniquely identifies each module."
	    ::= { gslamAGAlarmModuleEntry 1 }

	gslamAGAlarmModuleType	OBJECT-TYPE
		SYNTAX EquipmentTypeValue
 	 	MAX-ACCESS  read-only
 	 	STATUS      current
 	 	DESCRIPTION
			"Indicates the equipment type of this GSLAM-AG alarm module."
 	 	::= { gslamAGAlarmModuleEntry 2 }

	gslamAGAlarmModuleLocation		OBJECT-TYPE
		SYNTAX		LocationValue
		MAX-ACCESS	read-only
		STATUS		current
		DESCRIPTION
			"Indicate the location code of this GSLAM-AG alarm module."
	    ::= { gslamAGAlarmModuleEntry 3 }

	gslamAGAlarmModuleCLEI		OBJECT-TYPE
		SYNTAX		CLEIValue
		MAX-ACCESS	read-write
		STATUS		current
		DESCRIPTION
			"Indicate the CLEI code of this GSLAM-AG alarm module."
	    ::= { gslamAGAlarmModuleEntry 4 }

	gslamAGAlarmModulePrimaryState	OBJECT-TYPE
		SYNTAX	PrimaryStateValue
 	 	MAX-ACCESS  read-only
 	 	STATUS      current
 	 	DESCRIPTION
			"Indicates the primary state of this GSLAM-AG alarm module."
 	 	::= { gslamAGAlarmModuleEntry 5 }

	gslamAGAlarmModuleSecondaryState	OBJECT-TYPE
		SYNTAX	SecondaryStateValue
 	 	MAX-ACCESS  read-only
 	 	STATUS      current
 	 	DESCRIPTION
			"Indicates the secondary state of this GSLAM-AG alarm module."
 	 	::= { gslamAGAlarmModuleEntry 6 }

 	 gslamAGAlarmModuleHWManufactureName		OBJECT-TYPE
		SYNTAX		HWManufactureNameValue
		MAX-ACCESS	read-only
		STATUS		current
		DESCRIPTION
			"Indicate hardware manufacture name of this GSLAM-AG alarm module."
	    ::= { gslamAGAlarmModuleEntry 7 }

	gslamAGAlarmModuleHWManufactureSerial		OBJECT-TYPE
		SYNTAX		HWManufactureSerialValue
		MAX-ACCESS	read-only
		STATUS		current
		DESCRIPTION
			"Indicate hardware manufacture serial number of this GSLAM-AG alarm module."
	    ::= { gslamAGAlarmModuleEntry 8 }

	gslamAGAlarmModuleHWRevision		OBJECT-TYPE
		SYNTAX		HWRevisionValue
		MAX-ACCESS	read-only
		STATUS		current
		DESCRIPTION
			"Indicate hardware revision of this GSLAM-AG alarm module."
	    ::= { gslamAGAlarmModuleEntry 9 }

	gslamAGAlarmModuleHWManufacturePartName	OBJECT-TYPE
		SYNTAX      HWPartNumberValue
		MAX-ACCESS  read-only
		STATUS      current
		DESCRIPTION
			"Indicate hardware manufacture part name about this
			GSLAM-AG alarm module."
	    ::= { gslamAGAlarmModuleEntry 10 }

	gslamAGAlarmModuleHWManufacturePartNumber      OBJECT-TYPE
		SYNTAX      HWPartNumberValue
		MAX-ACCESS  read-only
		STATUS      current
		DESCRIPTION
			"Indicate hardware manufacture part number about this
			GSLAM-AG alarm module."
	    ::= { gslamAGAlarmModuleEntry 11 }

	--UV 5.0 START

	-- alarm module objects
	gslamAGREL50AlarmModuleTable		OBJECT-TYPE
		SYNTAX		SEQUENCE OF GslamAGREL50AlarmModuleEntry
		MAX-ACCESS	not-accessible
		STATUS		current
		DESCRIPTION
			"A table about the alarm modules of GSLAM-AG."
	    ::= { ipiGslamAGAlarmModuleObjs 2 }

	gslamAGREL50AlarmModuleEntry OBJECT-TYPE
		SYNTAX  		GslamAGREL50AlarmModuleEntry
		MAX-ACCESS	not-accessible
		STATUS  		current
		DESCRIPTION
			"A row in alarm module table.
			Entries can't be deleted or created via SNMP ops."
		INDEX   { gslamAGREL50ShelfIndex, gslamAGREL50AlarmModuleIndex }
	    ::= { gslamAGREL50AlarmModuleTable 1 }

	GslamAGREL50AlarmModuleEntry ::= SEQUENCE {
		gslamAGREL50AlarmModuleIndex	Unsigned32,
		gslamAGREL50AlarmModuleType		EquipmentTypeValue,
		gslamAGREL50AlarmModuleLocation	LocationValue,
		gslamAGREL50AlarmModuleCLEI		CLEIValue,
		gslamAGREL50AlarmModulePrimaryState				PrimaryStateValue,
		gslamAGREL50AlarmModuleSecondaryState			SecondaryStateValue,
		gslamAGREL50AlarmModuleHWManufactureName		HWManufactureNameValue,
		gslamAGREL50AlarmModuleHWManufactureSerial	HWManufactureSerialValue,
		gslamAGREL50AlarmModuleHWRevision				HWRevisionValue,
		gslamAGREL50AlarmModuleHWManufacturePartName  HWPartNumberValue,
		gslamAGREL50AlarmModuleHWManufacturePartNumber	HWPartNumberValue
	}

	gslamAGREL50AlarmModuleIndex	OBJECT-TYPE
		SYNTAX		Unsigned32
		MAX-ACCESS	not-accessible
		STATUS		current
		DESCRIPTION
			"Index of GSLAM-AG Alarm module table. It uniquely identifies each module."
	    ::= { gslamAGREL50AlarmModuleEntry 1 }

	gslamAGREL50AlarmModuleType	OBJECT-TYPE
		SYNTAX EquipmentTypeValue
 	 	MAX-ACCESS  read-only
 	 	STATUS      current
 	 	DESCRIPTION
			"Indicates the equipment type of this GSLAM-AG alarm module."
 	 	::= { gslamAGREL50AlarmModuleEntry 2 }

	gslamAGREL50AlarmModuleLocation		OBJECT-TYPE
		SYNTAX		LocationValue
		MAX-ACCESS	read-only
		STATUS		current
		DESCRIPTION
			"Indicate the location code of this GSLAM-AG alarm module."
	    ::= { gslamAGREL50AlarmModuleEntry 3 }

	gslamAGREL50AlarmModuleCLEI		OBJECT-TYPE
		SYNTAX		CLEIValue
		MAX-ACCESS	read-write
		STATUS		current
		DESCRIPTION
			"Indicate the CLEI code of this GSLAM-AG alarm module."
	    ::= { gslamAGREL50AlarmModuleEntry 4 }

	gslamAGREL50AlarmModulePrimaryState	OBJECT-TYPE
		SYNTAX	PrimaryStateValue
 	 	MAX-ACCESS  read-only
 	 	STATUS      current
 	 	DESCRIPTION
			"Indicates the primary state of this GSLAM-AG alarm module."
 	 	::= { gslamAGREL50AlarmModuleEntry 5 }

	gslamAGREL50AlarmModuleSecondaryState	OBJECT-TYPE
		SYNTAX	SecondaryStateValue
 	 	MAX-ACCESS  read-only
 	 	STATUS      current
 	 	DESCRIPTION
			"Indicates the secondary state of this GSLAM-AG alarm module."
 	 	::= { gslamAGREL50AlarmModuleEntry 6 }

 	 gslamAGREL50AlarmModuleHWManufactureName		OBJECT-TYPE
		SYNTAX		HWManufactureNameValue
		MAX-ACCESS	read-only
		STATUS		current
		DESCRIPTION
			"Indicate hardware manufacture name of this GSLAM-AG alarm module."
	    ::= { gslamAGREL50AlarmModuleEntry 7 }

	gslamAGREL50AlarmModuleHWManufactureSerial		OBJECT-TYPE
		SYNTAX		HWManufactureSerialValue
		MAX-ACCESS	read-only
		STATUS		current
		DESCRIPTION
			"Indicate hardware manufacture serial number of this GSLAM-AG alarm module."
	    ::= { gslamAGREL50AlarmModuleEntry 8 }

	gslamAGREL50AlarmModuleHWRevision		OBJECT-TYPE
		SYNTAX		HWRevisionValue
		MAX-ACCESS	read-only
		STATUS		current
		DESCRIPTION
			"Indicate hardware revision of this GSLAM-AG alarm module."
	    ::= { gslamAGREL50AlarmModuleEntry 9 }

	gslamAGREL50AlarmModuleHWManufacturePartName	OBJECT-TYPE
		SYNTAX      HWPartNumberValue
		MAX-ACCESS  read-only
		STATUS      current
		DESCRIPTION
			"Indicate hardware manufacture part name about this
			GSLAM-AG alarm module."
	    ::= { gslamAGREL50AlarmModuleEntry 10 }

	gslamAGREL50AlarmModuleHWManufacturePartNumber      OBJECT-TYPE
		SYNTAX      HWPartNumberValue
		MAX-ACCESS  read-only
		STATUS      current
		DESCRIPTION
			"Indicate hardware manufacture part number about this
			GSLAM-AG alarm module."
	    ::= { gslamAGREL50AlarmModuleEntry 11 }


	-- UV 5.0 END

	-- port objects
	gslamAGPortTable		OBJECT-TYPE
		SYNTAX		SEQUENCE OF GslamAGPortEntry
		MAX-ACCESS	not-accessible
		STATUS		current
		DESCRIPTION
			"A table about the port info of GSLAM-AG."
	    ::= { ipiGslamAGPortObjs 1 }

	gslamAGPortEntry OBJECT-TYPE
		SYNTAX  		GslamAGPortEntry
		MAX-ACCESS	not-accessible
		STATUS  		current
		DESCRIPTION
			"A row in port table.
			Entries can't be deleted or created via SNMP ops."
		INDEX   { gslamAGShelfIndex, gslamAGIOModuleIndex, gslamAGPortIndex }
	    ::= { gslamAGPortTable 1 }


	GslamAGPortEntry ::= SEQUENCE {
		gslamAGPortIndex		    Unsigned32,
		gslamAGPortIfIndex		    Unsigned32,
		gslamAGPortType			    EquipmentTypeValue,
		gslamAGPortAction		    ActionValue,
		gslamAGPortRowStatus		RowStatus,
		gslamAGPortCLEI			    CLEIValue,
		gslamAGPortPrimaryState		PrimaryStateValue,
		gslamAGPortSecondaryState	SecondaryStateValue,
		gslamAGPortWavelength		WavelengthValue, -- FREQ
		gslamAGPortProtFunction		ProtectionEntityValue, -- PROTN
		gslamAGPortClearDelay		Unsigned32,	-- CLRDLY
		gslamAGPortDropPacket		FlagValue,	-- DROPPKT
		gslamAGPortECC			    FlagValue,	-- ECC
		gslamAGPortIfDirection		IfDirValue,  	-- IF
		gslamAGPortLossBudget		TcvrReachValue,	-- LOSSB
		gslamAGPortNDP			    FlagValue,	-- NDP
		gslamAGPortSFThreshold		Unsigned32,	-- SFTH
		gslamAGPortSDThreshold		Unsigned32,	-- SDTH
		gslamAGPortSESThreshold		Unsigned32,	-- SESTH
		gslamAGPortTxOptPower		OCTET STRING,
		gslamAGPortRxOptPower		OCTET STRING,
		gslamAGPortTxOptMonLev  	OCTET STRING,	-- OPRMONLEV
		gslamAGPortRxOptMonLev  	OCTET STRING,   -- OPTMONLEV
		gslamAGPortProtocolCap  	ProtocolCapValue, -- PROTCAP
		gslamAGPortClassCap     	ClassCapValue,	-- CLASSCAP
		gslamAGPortDataFieldSize    Unsigned32,	-- DATAFLDSZ
		gslamAGPortSESSThreshold    Unsigned32,	-- SESSTH
		gslamAGPortCSESThreshold    Unsigned32,	-- CSESTH
		gslamAGPortFEC		      	FECValue,  -- FEC
		gslamAGPortMedium       	MediumValue,	-- MEDIUM
		gslamAGPortLineCoding   	LineCodingValue, -- LINECDE
		gslamAGPortTiming       	TimingValue,	-- TMG
		gslamAGPortDegMonLev    	Unsigned32,	-- DEGM
		gslamAGPortDegThreshold 	Integer32,	-- DEGTHR
		gslamAGPortGCC0     		FlagValue,	-- GCC0
		gslamAGPortTIMDetectMode    TIMModeValue,	-- TIMDETM
		gslamAGPortTIMActDisable    FlagValue,	-- TIMACTDIS
		gslamAGPortExpSAPI      	OCTET STRING,	-- EXPSAPI
		gslamAGPortExpDAPI      	OCTET STRING,   -- EXPDAPI
		gslamAGPortExpOperSpecified  OCTET STRING,   -- EXPOPR
		gslamAGPortTrcSAPI      	OCTET STRING,	-- TRCSAPI
		gslamAGPortTrcDAPI      	OCTET STRING,	-- TRCDAPI
		gslamAGPortTrcOperSpecified  OCTET STRING,   -- TRCOPR
		gslamAGPortReceivedTrcSAPI	OCTET STRING,
		gslamAGPortReceivedTrcDAPI  OCTET STRING,
		gslamAGPortReceivedTrcOperSpecified  OCTET STRING,
		gslamAGPortDirection    	INTEGER,	-- PDIRN
		gslamAGPortHWManufactureName    HWManufactureNameValue,
		gslamAGPortHWManufactureSerial  HWManufactureSerialValue,
		gslamAGPortHWRevision       	HWRevisionValue,
		gslamAGPortHWManufacturePartName	HWPartNumberValue,
		gslamAGPortHWManufacturePartNumber      HWPartNumberValue,
		gslamAGPortMuxStructure     INTEGER,
		gslamAGPortCompatability	IfDirValue,
		gslamAGPortAutoNegotiation	PortAutoNegotiationValue,
		gslamAGPortCableType		EEPortCableTypeValue,
		gslamAGPortLoopbackDuration	Unsigned32,
		gslamAGPortLaserMode		LaserModeValue,
		gslamAGPortSignalMapping	SignalMappingValue,
		gslamAGPortLOSLevel		OCTET STRING,
		gslamAGPortOSCTxPower  		OCTET STRING,   -- osc-txpower
		gslamAGPortOSCRxPower  		OCTET STRING,   -- osc-rxpower
		gslamAGPortOSCTxOptMonLev  	OCTET STRING,	-- osc-optmonlev
		gslamAGPortOSCRxOptMonLev  	OCTET STRING,   -- osc-oprmonlev
		gslamAGPortTxSpanLoss  		OCTET STRING,   -- tx span loss
		gslamAGPortRxSpanLoss  		OCTET STRING,   -- rx span loss
		gslamAGPortOSLRxMonLev  	OCTET STRING,   -- oslrmon-lev
		gslamAGPortOSLTxMonLev  	OCTET STRING,   -- osltmon-lev
		gslamAGPortActualLBC  		OCTET STRING,   -- actual-lbc
		gslamAGPortLBCMonLev  		OCTET STRING,   -- lbc-monlev
		gslamAGPortAttenuation		OCTET STRING,
		gslamAGPortMaxFrameSize		Unsigned32,
		gslamAGPortSpanLoss		FlagValue,
		gslamAGPortFreqChannel		FreqChannelNumValue,
		gslamAGPortLabel		OCTET STRING,
		gslamAGPortVideoFrameType	INTEGER,
		gslamAGPortSpeed		INTEGER,
		gslamAGPortGfpOutGoingUPI	OCTET STRING,
		gslamAGPortGfpIncomingUPI	OCTET STRING,
		gslamAGPortGfpExpectedUPI	OCTET STRING,
		gslamAGPortLOSClearLevel	OCTET STRING,
		gslamAGPortOOSLaserMode		LaserModeValue,
		gslamAGPortAISLAction		FlagValue,
		gslamAGPortPCSCoding		PCSCoding,
		gslamAGPortChanSize		   ChanSizeValue,
		gslamAGPortOperSpeed		INTEGER,
		gslamAGPortDuplexMode		DuplexMode,
        gslamAGPortLpbkType         INTEGER,
                gslamAGPortLOSThreshold         OCTET STRING,
		gslamAGPortAddress		OCTET STRING,
		gslamAGPortChannelType		INTEGER,	
		gslamAGPortFlowControl		FlagValue,
		gslamAGPortLaserXparency	FlagValue, 
		gslamAGPortLoopTiming		FlagValue,
		gslamAGPortSwitchNotification	INTEGER,
		gslamAGPortSwitchDuration	INTEGER,
		gslamAGPortLinkInitMode 	INTEGER,
		gslamAGPortNegotiationTimer	INTEGER,
		gslamAGPortLinkFailureTimer	INTEGER,
		gslamAGPortSpeedNegotiation	INTEGER,
		gslamAGPortCrdtMode		INTEGER,
		gslamAGPortCrdtValue		INTEGER,
		gslamAGPortCrdtRecoveryTimer	INTEGER,
		gslamAGPortFaultNotification	INTEGER,
		gslamAGPortFaultHoldOffDuration	INTEGER,
		gslamAGPortTimingMode		INTEGER,
		gslamAGPortECCRate		INTEGER,
		gslamAGPortAssociate		INTEGER,
		gslamAGPortRemoteVfptId		INTEGER,
		gslamAGPortMaxUtilization	INTEGER,
		gslamAGPortMinIPG		Unsigned32,
		gslamAGPortLocalCondition	OCTET STRING,
		gslamAGPortRemoteCondition	OCTET STRING,
		gslamAGPortOspfAdminStatus	INTEGER,
		gslamAGPortOspfProfileId	Unsigned32,
		gslamAGPortOspfProfileName	OCTET STRING,
		gslamAGPortOspfCost		Integer32
	}

	gslamAGPortIndex	OBJECT-TYPE
		SYNTAX		Unsigned32
		MAX-ACCESS	not-accessible
		STATUS		current
		DESCRIPTION
			"Index of GSLAM-AG port table. It uniquely identifies
			each port."
	    ::= { gslamAGPortEntry 1 }

	gslamAGPortIfIndex	OBJECT-TYPE
		SYNTAX		Unsigned32
		MAX-ACCESS	read-only
		STATUS		current
		DESCRIPTION
			"Indicate the ifIndex of Mib2's interface table of this
			GSLAM-AG port."
	    ::= { gslamAGPortEntry 2 }

	gslamAGPortType	OBJECT-TYPE
		SYNTAX		EquipmentTypeValue
		MAX-ACCESS	read-write
		STATUS		current
		DESCRIPTION
			"Indicate the equipment type of this GSLAM-AG port."
	    ::= { gslamAGPortEntry 3 }

	gslamAGPortAction			OBJECT-TYPE
		SYNTAX		ActionValue
		MAX-ACCESS	read-write
		STATUS		current
		DESCRIPTION
			"Indicate command issued to this GSLAM-AG port."
		::= { gslamAGPortEntry 4 }

	gslamAGPortRowStatus		OBJECT-TYPE
		SYNTAX		RowStatus
		MAX-ACCESS	read-create
		STATUS		current
		DESCRIPTION
			"Current status of this GSLAM-AG port entry."
	    ::= { gslamAGPortEntry 5 }

	gslamAGPortCLEI		OBJECT-TYPE
		SYNTAX		CLEIValue
		MAX-ACCESS	read-write
		STATUS		current
		DESCRIPTION
			"Indicate the CLEI code about this GSLAM-AG port."
	::= { gslamAGPortEntry 6 }

	gslamAGPortPrimaryState	OBJECT-TYPE
		SYNTAX	PrimaryStateValue
 	 	MAX-ACCESS  read-write
 	 	STATUS      current
 	 	DESCRIPTION
			"Indicates the primary state of this GSLAM-AG port."
 	 	::= { gslamAGPortEntry 7 }

	gslamAGPortSecondaryState	OBJECT-TYPE
		SYNTAX	SecondaryStateValue
 	 	MAX-ACCESS  read-only
 	 	STATUS      current
 	 	DESCRIPTION
			"Indicates the secondary state of this GSLAM-AG port."
 	 	::= { gslamAGPortEntry 8 }

	gslamAGPortWavelength	OBJECT-TYPE
		SYNTAX	WavelengthValue
		MAX-ACCESS  read-only
		STATUS      current
		DESCRIPTION
			"Indicates the wavelength of this GSLAM-AG port."
		::= { gslamAGPortEntry 9 }

	gslamAGPortProtFunction	OBJECT-TYPE
		SYNTAX	ProtectionEntityValue
		MAX-ACCESS  read-only
		STATUS      current
		DESCRIPTION
			"Indicates the protection function of this GSLAM-AG	port."
		::= { gslamAGPortEntry 10 }

	gslamAGPortClearDelay	OBJECT-TYPE
		SYNTAX	Unsigned32
		MAX-ACCESS  read-write
		STATUS      current
		DESCRIPTION
			"Indicates the hysteresis time for port faults of this GSLAM-AG
			port."
		::= { gslamAGPortEntry 11 }

	gslamAGPortDropPacket	OBJECT-TYPE
		SYNTAX	FlagValue
		MAX-ACCESS  read-write
		STATUS      current
		DESCRIPTION
			"Indicates the drop errors on transmit flag of this GSLAM-AG port."
		::= { gslamAGPortEntry 12 }

	gslamAGPortECC	OBJECT-TYPE
		SYNTAX	FlagValue
		MAX-ACCESS  read-write
		STATUS      current
		DESCRIPTION
			"Indicates the ECC (embedded comm channel) flag of this
	    GSLAM-AG port."
		::= { gslamAGPortEntry 13 }

	gslamAGPortIfDirection	OBJECT-TYPE
		SYNTAX	IfDirValue
		MAX-ACCESS  read-write
		STATUS      current
		DESCRIPTION
			"Indicates the interface direction of this GSLAM-AG port."
		::= { gslamAGPortEntry 14 }

	gslamAGPortLossBudget	OBJECT-TYPE
		SYNTAX	TcvrReachValue
		MAX-ACCESS  read-only
		STATUS      current
		DESCRIPTION
			"Indicates the range of transciever in this GSLAM-AG port."
		::= { gslamAGPortEntry 15 }

	gslamAGPortNDP	OBJECT-TYPE
		SYNTAX	FlagValue
		MAX-ACCESS  read-write
		STATUS      current
		DESCRIPTION
			"Indicates the NDP flag of this GSLAM-AG port."
		::= { gslamAGPortEntry 16 }

	gslamAGPortSFThreshold		OBJECT-TYPE
		SYNTAX	Unsigned32
		MAX-ACCESS  read-write
		STATUS      current
		DESCRIPTION
			"Indicates the signal fail threshold value of this GSLAM-AG port."
		::= { gslamAGPortEntry 17 }

	 gslamAGPortSDThreshold		OBJECT-TYPE
		SYNTAX	Unsigned32
		MAX-ACCESS  read-write
		STATUS      current
		DESCRIPTION
			"Indicates the signal degrade threshold value of this GSLAM-AG
			port."
		::= { gslamAGPortEntry 18 }

	gslamAGPortSESThreshold		OBJECT-TYPE
		SYNTAX	Unsigned32
		MAX-ACCESS  read-write
		STATUS      current
		DESCRIPTION
			"Indicates the severely errored seconds declaration
				    threshold value of this GSLAM-AG port."
		::= { gslamAGPortEntry 19 }

	gslamAGPortTxOptPower	OBJECT-TYPE
		SYNTAX		OCTET STRING(SIZE(1..15))
		MAX-ACCESS	read-only
		STATUS		current
		DESCRIPTION
			"Indicate the transmitted optical power of this
				    GSLAM-AG port."
		::= { gslamAGPortEntry 20 }

	gslamAGPortRxOptPower	OBJECT-TYPE
		SYNTAX		OCTET STRING(SIZE(1..15))
		MAX-ACCESS	read-only
		STATUS		current
		DESCRIPTION
			"Indicate the received optical power of this GSLAM-AG port."
		::= { gslamAGPortEntry 21 }

    gslamAGPortTxOptMonLev  OBJECT-TYPE
       	SYNTAX      OCTET STRING(SIZE(1..15))
       	MAX-ACCESS  read-write
       	STATUS      current
       	DESCRIPTION
       		"Indicate the nominal transmit optical power of this GSLAM-AG
       		port."
       	::= { gslamAGPortEntry 22 }

    gslamAGPortRxOptMonLev  OBJECT-TYPE
       	SYNTAX      OCTET STRING(SIZE(1..15))
       	MAX-ACCESS  read-write
       	STATUS      current
       	DESCRIPTION
       		"Indicate the nominal received optical power of this GSLAM-AG
       		port."
       	::= { gslamAGPortEntry 23 }

	gslamAGPortProtocolCap      OBJECT-TYPE
	SYNTAX  ProtocolCapValue
       	MAX-ACCESS  read-only
       	STATUS      current
       	DESCRIPTION
       		"Indicates the protocol capability of this GSLAM-AG port."
	::= { gslamAGPortEntry 24 }

    gslamAGPortClassCap     OBJECT-TYPE
       	SYNTAX  ClassCapValue
       	MAX-ACCESS  read-only
       	STATUS      current
       	DESCRIPTION
       		"Indicates the class capability of this GSLAM-AG port."
       	::= { gslamAGPortEntry 25 }

    gslamAGPortDataFieldSize	OBJECT-TYPE
       	SYNTAX  Unsigned32
       	MAX-ACCESS  read-only
       	STATUS      current
       	DESCRIPTION
       		"Indicates the data field size of this GSLAM-AG port."
       	::= { gslamAGPortEntry 26 }

    gslamAGPortSESSThreshold	OBJECT-TYPE
       	SYNTAX  Unsigned32
       	MAX-ACCESS  read-write
       	STATUS      current
       	DESCRIPTION
       		"Indicates the signal errored seconds declaration
    	    threshold value of this GSLAM-AG port."
       	::= { gslamAGPortEntry 27 }

   	gslamAGPortCSESThreshold	OBJECT-TYPE
       	SYNTAX  Unsigned32
       	MAX-ACCESS  read-write
       	STATUS      current
       	DESCRIPTION
       		"Indicates the consecutive signal errored seconds
   		    declaration threshold value of this GSLAM-AG port."
       	::= { gslamAGPortEntry 28 }

	gslamAGPortFEC  OBJECT-TYPE
		SYNTAX  FECValue
		MAX-ACCESS  read-write
		STATUS      current
		DESCRIPTION
			"Indicates the forward error code flag of this GSLAM-AG
			port."
		::= { gslamAGPortEntry 29 }

    gslamAGPortMedium	   OBJECT-TYPE
       	SYNTAX  MediumValue
       	MAX-ACCESS  read-only
       	STATUS      current
       	DESCRIPTION
       		"Indicates the medium type of this GSLAM-AG port."
       	::= { gslamAGPortEntry 30 }

   	gslamAGPortLineCoding       OBJECT-TYPE
       	SYNTAX  LineCodingValue
       	MAX-ACCESS  read-only
       	STATUS      current
       	DESCRIPTION
       		"Indicates the line coding value of this GSLAM-AG port."
       	::= { gslamAGPortEntry 31 }

    gslamAGPortTiming	   OBJECT-TYPE
       	SYNTAX  TimingValue
       	MAX-ACCESS  read-only
       	STATUS      current
       	DESCRIPTION
       		"Indicates the timing value of this GSLAM-AG port."
       	::= { gslamAGPortEntry 32 }

     gslamAGPortDegMonLev   OBJECT-TYPE
       	SYNTAX  Unsigned32
       	MAX-ACCESS  read-write
       	STATUS      current
       	DESCRIPTION
       		"Indicates the degrade monitored level value of this
     	    GSLAM-AG port."
       	::= { gslamAGPortEntry 33 }

     gslamAGPortDegThreshold    OBJECT-TYPE
       	SYNTAX  Integer32
       	MAX-ACCESS  read-write
       	STATUS      current
       	DESCRIPTION
       		"Indicates the degrade threshold value (percentage of
     	    errored blocks)	of this GSLAM-AG port. -1 mean not applicable"
       	::= { gslamAGPortEntry 34 }

    gslamAGPortGCC0     OBJECT-TYPE
       	SYNTAX      FlagValue
       	MAX-ACCESS  read-write
       	STATUS      current
       	DESCRIPTION
       		"Indicate the GCC0 value of this GSLAM-AG port."
       	::= { gslamAGPortEntry 35 }

    gslamAGPortTIMDetectMode OBJECT-TYPE
       	SYNTAX  TIMModeValue
       	MAX-ACCESS  read-write
       	STATUS      current
       	DESCRIPTION
       		"Indicates the TIM detection mode value of this GSLAM-AG port."
       	::= { gslamAGPortEntry 36 }

    gslamAGPortTIMActDisable OBJECT-TYPE
       	SYNTAX  FlagValue
       	MAX-ACCESS  read-write
       	STATUS      current
       	DESCRIPTION
       		"Indicates the TIM consequent action value of this GSLAM-AG port."
       	::= { gslamAGPortEntry 37 }

    gslamAGPortExpSAPI      OBJECT-TYPE
       	SYNTAX      OCTET STRING(SIZE(0..15))
       	MAX-ACCESS  read-write
       	STATUS      current
       	DESCRIPTION
       		"Indicate the expected SAPI value of this GSLAM-AG port."
	::= { gslamAGPortEntry 38 }

    gslamAGPortExpDAPI      OBJECT-TYPE
       	SYNTAX      OCTET STRING(SIZE(0..15))
       	MAX-ACCESS  read-write
       	STATUS      current
       	DESCRIPTION
       		"Indicate the expected DAPI value of this GSLAM-AG port."
	::= { gslamAGPortEntry 39 }

   	gslamAGPortExpOperSpecified  OBJECT-TYPE
       	SYNTAX      OCTET STRING(SIZE(0..32))
       	MAX-ACCESS  read-write
       	STATUS      current
       	DESCRIPTION
      		"Indicate the expected operator specified value of this
   		    GSLAM-AG port."
       	::= { gslamAGPortEntry 40 }

   	gslamAGPortTrcSAPI      OBJECT-TYPE
       	SYNTAX      OCTET STRING(SIZE(0..15))
       	MAX-ACCESS  read-write
       	STATUS      current
       	DESCRIPTION
       		"Indicate the transmitted SAPI value of this GSLAM-AG port."
       	::= { gslamAGPortEntry 41 }

	gslamAGPortTrcDAPI      OBJECT-TYPE
       	SYNTAX      OCTET STRING(SIZE(0..15))
       	MAX-ACCESS  read-write
       	STATUS      current
       	DESCRIPTION
       		"Indicate the transmitted DAPI value of this GSLAM-AG port."
	::= { gslamAGPortEntry 42 }

    gslamAGPortTrcOperSpecified  OBJECT-TYPE
       	SYNTAX      OCTET STRING(SIZE(0..32))
       	MAX-ACCESS  read-write
       	STATUS      current
       	DESCRIPTION
       		"Indicate the transmitted operator specified value of
   		    this GSLAM-AG port."
       	::= { gslamAGPortEntry 43 }

    gslamAGPortReceivedTrcSAPI      OBJECT-TYPE
	SYNTAX      OCTET STRING(SIZE(0..15))
	MAX-ACCESS  read-only
	STATUS      current
	DESCRIPTION
	    "Indicate the received SAPI value of this GSLAM-AG port."
	::= { gslamAGPortEntry 44 }

    gslamAGPortReceivedTrcDAPI      OBJECT-TYPE
	SYNTAX      OCTET STRING(SIZE(0..15))
	MAX-ACCESS  read-only
	STATUS      current
	DESCRIPTION
	    "Indicate the received DAPI value of this GSLAM-AG port."
	::= { gslamAGPortEntry 45 }

    gslamAGPortReceivedTrcOperSpecified  OBJECT-TYPE
	SYNTAX      OCTET STRING(SIZE(0..32))
	MAX-ACCESS  read-only
	STATUS      current
	DESCRIPTION
	    "Indicate the received operator specified value of this
	    GSLAM-AG port."
	::= { gslamAGPortEntry 46 }

    gslamAGPortDirection    OBJECT-TYPE
	SYNTAX      INTEGER {
	    unknown(1),
	    not-present(2),
	    rcv(3),
	    trmt(4),
	    rcv-trmt(5),
	    uni-rcv-trmt(6)
	}
	MAX-ACCESS  read-write
	STATUS      current
	DESCRIPTION
	    "Indicates the data direction of this GSLAM-AG port."
	::= { gslamAGPortEntry 47 }

    gslamAGPortHWManufactureName       OBJECT-TYPE
	SYNTAX      HWManufactureNameValue
	MAX-ACCESS  read-only
	STATUS      current
	DESCRIPTION
	    "Indicate hardware manufacture name about this GSLAM-AG
	    port."
	::= { gslamAGPortEntry 48 }

    gslamAGPortHWManufactureSerial      OBJECT-TYPE
	SYNTAX      HWManufactureSerialValue
	MAX-ACCESS  read-only
	STATUS      current
	DESCRIPTION
	    "Indicate hardware manufacture serial number about this
	    GSLAM-AG port."
	::= { gslamAGPortEntry 49 }

    gslamAGPortHWRevision       OBJECT-TYPE
	SYNTAX      HWRevisionValue
	MAX-ACCESS  read-only
	STATUS      current
	DESCRIPTION
	    "Indicate hardware revision about this GSLAM-AG port."
	::= { gslamAGPortEntry 50 }

    gslamAGPortHWManufacturePartName	OBJECT-TYPE
	SYNTAX      HWPartNumberValue
	MAX-ACCESS  read-only
	STATUS      current
	DESCRIPTION
	    "Indicate hardware manufacture part name about this
	    GSLAM-AG port."
	::= { gslamAGPortEntry 51 }

    gslamAGPortHWManufacturePartNumber      OBJECT-TYPE
	SYNTAX      HWPartNumberValue
	MAX-ACCESS  read-only
	STATUS      current
	DESCRIPTION
	    "Indicate hardware manufacture part number about this
	    GSLAM-AG port."
	::= { gslamAGPortEntry 52 }

    gslamAGPortMuxStructure    OBJECT-TYPE
	SYNTAX      INTEGER {
	    unknown(1),
	    not-present(2),
	    channelized(3),
	    clear(4)
	}
	MAX-ACCESS  read-write
	STATUS      deprecated
	DESCRIPTION
	    "Indicates the multiplex structure for a port."
	::= { gslamAGPortEntry 53 }

    gslamAGPortCompatability	OBJECT-TYPE
		SYNTAX	IfDirValue
		MAX-ACCESS  read-write
		STATUS      current
		DESCRIPTION
			"Indicate whether the gbe interface can be configured as
			 network or client port during firmware upgrade. "
		::= { gslamAGPortEntry 54 }

    gslamAGPortAutoNegotiation	OBJECT-TYPE
		SYNTAX	PortAutoNegotiationValue
		MAX-ACCESS  read-write
		STATUS      current
		DESCRIPTION
			"Indicate whether the electrical/cu interface can be set
			 to for autonegotiation for right bandwidth. "
		::= { gslamAGPortEntry 55 }

    gslamAGPortCableType	OBJECT-TYPE
		SYNTAX EEPortCableTypeValue
		MAX-ACCESS  read-write
		STATUS      current
		DESCRIPTION
			"Indicate whether the 1000TBase port to swap signal pair
			 to accomodate the specified type of RJ-45 cable type
			 that is connected to the port.
			 Applicable to copper interfaces only."
		::= { gslamAGPortEntry 56 }

	gslamAGPortLoopbackDuration  OBJECT-TYPE
       		SYNTAX  Unsigned32
       		MAX-ACCESS  read-write
       		STATUS      current
       		DESCRIPTION
       			" This is an write only object that specifies the duration to
       			loopback. Loopback terminates after the expiry of time interval."
       		::= { gslamAGPortEntry 57 }

	gslamAGPortLaserMode	OBJECT-TYPE
		SYNTAX LaserModeValue
		MAX-ACCESS  read-write
		STATUS      current
		DESCRIPTION
			"Defines the laser(transmitter) bahaviour based
			 up on detection of a failure condition on the
			 incoming signal at an optical facility interface."
		::= { gslamAGPortEntry 58 }

	gslamAGPortSignalMapping	OBJECT-TYPE
		SYNTAX SignalMappingValue
		MAX-ACCESS  read-write
		STATUS      current
		DESCRIPTION
			"Defines the mapping for transporting the 10GbE LAN
			 client signal over OTN OTU2/OTU2e, OC-192, or STM-64 signal."
		::= { gslamAGPortEntry 59 }

	gslamAGPortLOSLevel	OBJECT-TYPE
		SYNTAX OCTET STRING(SIZE(1..15))
		MAX-ACCESS  read-write
		STATUS      current
		DESCRIPTION
			"Threshold for declaring the LOS defect."
		::= { gslamAGPortEntry 60 }

	gslamAGPortOSCTxPower	OBJECT-TYPE
		SYNTAX OCTET STRING(SIZE(1..15))
		MAX-ACCESS  read-only
		STATUS      current
		DESCRIPTION
			"OSC Tx Power"
		::= { gslamAGPortEntry 61 }

	gslamAGPortOSCRxPower	OBJECT-TYPE
		SYNTAX OCTET STRING(SIZE(1..15))
		MAX-ACCESS  read-only
		STATUS      current
		DESCRIPTION
			"OSC Rx Power"
		::= { gslamAGPortEntry 62 }

	gslamAGPortOSCTxOptMonLev	OBJECT-TYPE
		SYNTAX OCTET STRING(SIZE(1..15))
		MAX-ACCESS  read-write
		STATUS      current
		DESCRIPTION
			"Indicates nominal transmitted power on OSC "
		::= { gslamAGPortEntry 63 }

	gslamAGPortOSCRxOptMonLev	OBJECT-TYPE
		SYNTAX OCTET STRING(SIZE(1..15))
		MAX-ACCESS  read-write
		STATUS      current
		DESCRIPTION
			"Indicates nominal receive power on OSC "
		::= { gslamAGPortEntry 64 }

	gslamAGPortTxSpanLoss	OBJECT-TYPE
		SYNTAX OCTET STRING(SIZE(1..15))
		MAX-ACCESS  read-only
		STATUS      current
		DESCRIPTION
			"Tx span loss"
		::= { gslamAGPortEntry 65 }

	gslamAGPortRxSpanLoss	OBJECT-TYPE
		SYNTAX OCTET STRING(SIZE(1..15))
		MAX-ACCESS  read-only
		STATUS      current
		DESCRIPTION
			"Rx span loss"
		::= { gslamAGPortEntry 66 }

	gslamAGPortOSLRxMonLev	OBJECT-TYPE
		SYNTAX OCTET STRING(SIZE(1..15))
		MAX-ACCESS  read-write
		STATUS      current
		DESCRIPTION
			"Indicates nominal receive span loss power"
		::= { gslamAGPortEntry 67 }

	gslamAGPortOSLTxMonLev	OBJECT-TYPE
		SYNTAX OCTET STRING(SIZE(1..15))
		MAX-ACCESS  read-write
		STATUS      current
		DESCRIPTION
			"Indicates nominal tramit span loss power"
		::= { gslamAGPortEntry 68 }

	gslamAGPortActualLBC	OBJECT-TYPE
		SYNTAX OCTET STRING(SIZE(1..15))
		MAX-ACCESS  read-only
		STATUS      current
		DESCRIPTION
			"Actual Laser Bias Current value."
		::= { gslamAGPortEntry 69 }

	gslamAGPortLBCMonLev	OBJECT-TYPE
		SYNTAX OCTET STRING(SIZE(1..15))
		MAX-ACCESS  read-only  -- write ??
		STATUS      current
		DESCRIPTION
			"Indicated nominal Laser Bias Current value."
		::= { gslamAGPortEntry 70 }

	gslamAGPortAttenuation	OBJECT-TYPE
		SYNTAX OCTET STRING(SIZE(1..15))
		MAX-ACCESS  read-write
		STATUS      current
		DESCRIPTION
			"Used to add attenuation in order to adjust power
			 for individual optical channels."
		::= { gslamAGPortEntry 71 }

    	gslamAGPortMaxFrameSize	OBJECT-TYPE
       		SYNTAX  Unsigned32
       		MAX-ACCESS  read-write
       		STATUS      current
       		DESCRIPTION
       			"Indicates max frame size that can be sent over the interface."
       		::= { gslamAGPortEntry 72 }

	gslamAGPortSpanLoss      OBJECT-TYPE
		SYNTAX      FlagValue
		MAX-ACCESS  read-write
		STATUS      current
		DESCRIPTION
			"Indicates enable/disable the automatic gain adjustment of
			 the amplifier to offset the loss of previous transmission
			 fiber."
		::= { gslamAGPortEntry 73 }

	gslamAGPortFreqChannel      OBJECT-TYPE
		SYNTAX      FreqChannelNumValue
		MAX-ACCESS  read-write
		STATUS      current
		DESCRIPTION
			"Indicates frequency or channel number for tunable port."
		::= { gslamAGPortEntry 74 }

	gslamAGPortLabel	OBJECT-TYPE
		SYNTAX OCTET STRING(SIZE(1..32))
		MAX-ACCESS  read-only
		STATUS      current
		DESCRIPTION
			"Catalog label to uniquely identify and AID."
		::= { gslamAGPortEntry 75 }

	gslamAGPortVideoFrameType    OBJECT-TYPE
		SYNTAX      INTEGER {
	    		unknown (1),
	    		not-present (2),
	    		lines-525 (3),
	    		lines-625 (4)
		}
		MAX-ACCESS  read-write
		STATUS      current
		DESCRIPTION
	    	"Indicates the frame format of the component video in serial digital D1 video signal."
		::= { gslamAGPortEntry 76 }

	gslamAGPortSpeed    OBJECT-TYPE
		SYNTAX      INTEGER {
	    		unknown (1),
	    		not-present (2),
	    		mbps-10 (3),
	    		mbps-100 (4),
	    		gbps-1(5),
	    		gbps-10(6)
		}
		MAX-ACCESS  read-write
		STATUS      current
		DESCRIPTION
	    	"Indicates speed on 10/100Base-T Ethernet interface"
		::= { gslamAGPortEntry 77 }

	gslamAGPortGfpOutGoingUPI OBJECT-TYPE
		SYNTAX OCTET STRING(SIZE(1..20))
		MAX-ACCESS  read-only
		STATUS      current
		DESCRIPTION
			"Out going User Payload Identifier(UPI) value in payload
			 header of GFP-T/GFP-F framed client signal"
		::= { gslamAGPortEntry 78 }

	gslamAGPortGfpExpectedUPI	OBJECT-TYPE
		SYNTAX OCTET STRING(SIZE(1..20))
		MAX-ACCESS  read-only
		STATUS      current
		DESCRIPTION
			"Expected User Payload Identifier(UPI) value in payload
			 header of GFP-T/GFP-F framed client signal"
		::= { gslamAGPortEntry 79 }

	gslamAGPortGfpIncomingUPI OBJECT-TYPE
		SYNTAX OCTET STRING(SIZE(1..20))
		MAX-ACCESS  read-only
		STATUS      current
		DESCRIPTION
			"Incoming User Payload Identifier(UPI) value in payload
			 header of GFP-T/GFP-F framed client signal"
		::= { gslamAGPortEntry 80 }

	gslamAGPortLOSClearLevel	OBJECT-TYPE
		SYNTAX OCTET STRING(SIZE(1..15))
		MAX-ACCESS  read-write
		STATUS      current
		DESCRIPTION
			"Threshold for clearing the LOS defect."
		::= { gslamAGPortEntry 81 }

	gslamAGPortOOSLaserMode	OBJECT-TYPE
		SYNTAX LaserModeValue
		MAX-ACCESS  read-write
		STATUS      current
		DESCRIPTION
			"Defines the laser(transmitter) bahaviour for an
			 optical facility interface in OOS state."
		::= { gslamAGPortEntry 82 }

	gslamAGPortAISLAction	OBJECT-TYPE
		SYNTAX      FlagValue
		MAX-ACCESS  read-write
		STATUS      current
		DESCRIPTION
			"Indicates the consequence action when port in ais-l"
		::= { gslamAGPortEntry 83 }

	gslamAGPortPCSCoding	OBJECT-TYPE
		SYNTAX      PCSCoding
		MAX-ACCESS  read-write
		STATUS      current
		DESCRIPTION
			"Indicates the behavior of PCS layer at an
			 FC1200 Fiber Channel facility interface"
		::= { gslamAGPortEntry 84 }

	gslamAGPortChanSize	OBJECT-TYPE
		SYNTAX		ChanSizeValue
		MAX-ACCESS	read-write
		STATUS		current
		DESCRIPTION
			"OTNCG port channel size."
	    ::= { gslamAGPortEntry 85 }

	gslamAGPortOperSpeed		OBJECT-TYPE
		SYNTAX      INTEGER {
	    		unknown (1),
	    		not-present (2),
	    		mbps-10 (3),
	    		mbps-100 (4),
	    		gbps-1 (5),
	    		gbps-10 (6)
		}
		MAX-ACCESS  read-only
		STATUS      current
		DESCRIPTION
	    	"Indicates speed on 10/100/1000 Ethernet interface"
		::= { gslamAGPortEntry 86 }

				
	gslamAGPortDuplexMode	OBJECT-TYPE
		SYNTAX      DuplexMode
		MAX-ACCESS  read-only
		STATUS      current
		DESCRIPTION
			"full-duplex or half-duplex"
		::= { gslamAGPortEntry 87 }

    gslamAGPortLpbkType        OBJECT-TYPE
        SYNTAX      INTEGER {
                unknown (1),
                not-present (2),
                facility (3),
                terminal (4)   
        }
        MAX-ACCESS  read-only
        STATUS      current
        DESCRIPTION
            "Indicates loopback type on a port"
        ::= { gslamAGPortEntry 88 } 

        gslamAGPortLOSThreshold     OBJECT-TYPE
                SYNTAX  OCTET STRING(SIZE(1..8))
                MAX-ACCESS      read-only
                STATUS    current
                DESCRIPTION
                    "LOS threshold value for Raman module in dB "
                ::= { gslamAGPortEntry 89 }

-- ************** ESOM SUPPORT STARTS **************
  	gslamAGPortAddress      OBJECT-TYPE
		SYNTAX          OCTET STRING (SIZE(0..31))
		MAX-ACCESS      read-only
		STATUS          current
		DESCRIPTION
			"Indicate the MAC address of ESOM Card Module"
		::= { gslamAGPortEntry  90}

	gslamAGPortChannelType      OBJECT-TYPE
		SYNTAX          INTEGER {
					unknown(1),
					not-applicable(2),
					opvcx(3),
					vptch(4)
				} 
		MAX-ACCESS      read-write
		STATUS          current
		DESCRIPTION
			"Indicate the channel type of client port (opvcx | vptch)"
		::= { gslamAGPortEntry  91}	

	
	gslamAGPortFlowControl	OBJECT-TYPE
		SYNTAX          FlagValue 
		MAX-ACCESS      read-write
		STATUS          current
		DESCRIPTION
			"Indicate the flow control state of the port."
		::= { gslamAGPortEntry  92}

	gslamAGPortLaserXparency	OBJECT-TYPE
		SYNTAX          FlagValue 
		MAX-ACCESS      read-write
		STATUS          current
		DESCRIPTION
			"Indicate the laser transparency state of the port."
		::= { gslamAGPortEntry  93}

	gslamAGPortLoopTiming 	OBJECT-TYPE
			SYNTAX          FlagValue 
			MAX-ACCESS      read-write
			STATUS          current
			DESCRIPTION
				"Indicate the loop-timing mode for the selected SONET/SDH interface"
		::= { gslamAGPortEntry  94}
	
	gslamAGPortSwitchNotification 	OBJECT-TYPE
			SYNTAX          INTEGER {
						not-applicable(1),
						disabled(2),
						nos(3),
						lr(4),
						ud(5),
						breakLink(6),
						linkFail(7),
						laserWink(8)
						} 
			MAX-ACCESS      read-write
			STATUS          current
			DESCRIPTION
				"Indicate the Switch Notification state of the port."
		::= { gslamAGPortEntry  95}
		
	gslamAGPortSwitchDuration	OBJECT-TYPE
		SYNTAX          INTEGER (0 | 100..5000)
		MAX-ACCESS      read-write
		STATUS          current
		DESCRIPTION
	       "Indicate the duration with in which protection switch should occur across the port, 
			in multiples of 100ms. 0 value means disabled feature for this port"
		::= { gslamAGPortEntry  96}
		
	gslamAGPortLinkInitMode 	OBJECT-TYPE
		SYNTAX          INTEGER {
				not-applicable(1),
				transparent(2), 
				semi-transparent(3), 
				local(4)
				}	
		MAX-ACCESS      read-write
		STATUS          current
		DESCRIPTION
			"Indicate the link initialization state of the port."
		::= { gslamAGPortEntry  97}
	
	gslamAGPortNegotiationTimer 	OBJECT-TYPE
		SYNTAX          INTEGER (0 | 10..20)
		MAX-ACCESS      read-write
		STATUS          current
		DESCRIPTION
		       "Indicate the GbE Auto Negotiation Link Timer in ms.
				0 value means disabled feature for this port"
		::= { gslamAGPortEntry  98}

	gslamAGPortLinkFailureTimer	OBJECT-TYPE
		SYNTAX          INTEGER (0..200)
		MAX-ACCESS      read-write
		STATUS          current
		DESCRIPTION
		       "Indicate the breaklink detection persistence timer of GbE port in ms."
		::= { gslamAGPortEntry  99}

	gslamAGPortSpeedNegotiation	OBJECT-TYPE
		SYNTAX          INTEGER {
					not-applicable(1),
					auto(2),
					fc-1G(3), 
					fc-2G(4), 
					fc-4G(5)  
				}
		MAX-ACCESS      read-write
		STATUS          current
		DESCRIPTION
		       "Indicate the Gigabit Fiber Channel speed negotiation line rate of the port."
		::= { gslamAGPortEntry  100}
	
	gslamAGPortCrdtMode 	OBJECT-TYPE
		SYNTAX          INTEGER {
			not-applicable(1),
			auto(2), 
			manual(3)
			}
		MAX-ACCESS      read-write
		STATUS          current
		DESCRIPTION
			"Configure the GbFC buffer credit settings for FCHP port."
		::= { gslamAGPortEntry  101}
	gslamAGPortCrdtValue 	OBJECT-TYPE
		SYNTAX          INTEGER (0..255)
		MAX-ACCESS      read-write
		STATUS          current
		DESCRIPTION
			"Indicates CTx buffer to buffer credit value.
			0 value means disabled feature for this port"
		::= { gslamAGPortEntry  102}
	
	gslamAGPortCrdtRecoveryTimer 	OBJECT-TYPE
		SYNTAX          INTEGER (0..25000)
		MAX-ACCESS      read-write
		STATUS          current
		DESCRIPTION
			"Indicates the credit starvation recovery timer"
		::= { gslamAGPortEntry  103}
	
	gslamAGPortFaultNotification 	OBJECT-TYPE
		SYNTAX          INTEGER{
				not-applicable(1),
				disabled(2),
				nos(3), 
				ols(4), 
				breakLink(5), 
				linkFail(6), 
				linkOffLine(7),
				laserDisable(8)
		}
		MAX-ACCESS      read-write
		STATUS          current
		DESCRIPTION
	       "Indicate "
		::= { gslamAGPortEntry  104}

	gslamAGPortFaultHoldOffDuration 	OBJECT-TYPE
		SYNTAX          INTEGER(0..200)
		MAX-ACCESS      read-write
		STATUS          current
		DESCRIPTION
	       "Indicate the hold off duration for fault on port to get cleared"
		::= { gslamAGPortEntry  105}
	
	gslamAGPortTimingMode 	OBJECT-TYPE
		SYNTAX          INTEGER {
			not-applicable(1),
			self-timed(2), 
			loop-timed(3),
			freerun(4)
			}
		MAX-ACCESS      read-only
		STATUS          current
		DESCRIPTION
			"Indicate the Active Timing mode of the port."
		::= { gslamAGPortEntry  106}
	
	gslamAGPortECCRate 	OBJECT-TYPE
		SYNTAX		INTEGER {
				not-applicable(1),
				ibcc-64(2),
				ibcc-128(3),
				ibcc-192(4),
				ibcc-256(5),
				ibcc-320(6),
				ibcc-384(7),
				ibcc-448(8),
				ibcc-512(9),
				ibcc-576(10),
				ibcc-640(11),
				ibcc-704(12),
				ibcc-768(13),
				ibcc-832(14),
				ibcc-896(15),
				ibcc-960(16)
			}
		MAX-ACCESS      read-write
		STATUS          current
		DESCRIPTION
			"Indicate the maximum aggregated rate of the Embedded Communication Channels carried over the IBCC of the VFNT in context."
		::= { gslamAGPortEntry  107}

	gslamAGPortAssociate 	OBJECT-TYPE
		SYNTAX          INTEGER {
			not-applicable(1),
			otncg(2), 
			stncg(3),
			ptnrg(4)
			}
		MAX-ACCESS      read-write
		STATUS          current
		DESCRIPTION
			"Indicate the associated network channel terminating entity to VFNT interface"
	::= { gslamAGPortEntry  108}
	
	gslamAGPortRemoteVfptId	OBJECT-TYPE
		SYNTAX          INTEGER(0..12)
		MAX-ACCESS      read-write
		STATUS          current
		DESCRIPTION
	       "Indicate the the remote VFPT identifier provisioned against the local VFPT
			0 value means feature disabled for this port"
		::= { gslamAGPortEntry  109}
		
	gslamAGPortMaxUtilization 	OBJECT-TYPE
		SYNTAX          INTEGER(0..100)
		MAX-ACCESS      read-write
		STATUS          current
		DESCRIPTION
	       "Indicate the maximum egress utilization permitted on the ethernet interface, 
			as % of the gigabit ethernet nominal rate from 1% to 100%. 0 value means disabled feature for this port"
		::= { gslamAGPortEntry  110}
	
	gslamAGPortMinIPG	OBJECT-TYPE
		SYNTAX          Unsigned32	
		MAX-ACCESS      read-write
		STATUS          current
		DESCRIPTION
	       "Indicate the minimum IPG permitted to be transmitted on the ethernet interface, 
			in ns from 96ns to 1008ns of the port"
		::= { gslamAGPortEntry  111}

	gslamAGPortLocalCondition	OBJECT-TYPE
		SYNTAX          OCTET STRING (SIZE(0..31))
		MAX-ACCESS      read-only
		STATUS          current
		DESCRIPTION
		"Indicate the Local Fault Condition of the ESOM Port"
		::= { gslamAGPortEntry  112}
		
	gslamAGPortRemoteCondition	OBJECT-TYPE
		SYNTAX          OCTET STRING (SIZE(0..31))
		MAX-ACCESS      read-only
		STATUS          current
		DESCRIPTION
		"Indicate the Remote Fault Condition of the ESOM Port"
		::= { gslamAGPortEntry  113}
		
	gslamAGPortOspfAdminStatus  OBJECT-TYPE
		SYNTAX  INTEGER { enabled (1), disabled (2) }
		MAX-ACCESS  read-write
		STATUS  current
		DESCRIPTION
		"The administrative status of OSPF on this
		port.  The value 'enabled' denotes that OSPF
		protocol is active on that port and 'disabled'
		denotes that it is not."
		DEFVAL  { 2 }       -- Disabled
		::= { gslamAGPortEntry  121 }

	gslamAGPortOspfProfileId        OBJECT-TYPE
		SYNTAX  Unsigned32
		MAX-ACCESS  read-write
		STATUS  current
		DESCRIPTION
		"ID of the profile assigned to the port.
		The corresponding profile must exist."
		DEFVAL  { 1 }       -- default profile
		::= { gslamAGPortEntry  122 }

    gslamAGPortOspfProfileName        OBJECT-TYPE
        SYNTAX  OCTET STRING (SIZE (0..20))
        MAX-ACCESS  read-write
        STATUS  current
        DESCRIPTION
        "Name of the profile assigned to the port.
        The corresponding profile must exist."
        DEFVAL  { "Default" }       -- default profile
        ::= { gslamAGPortEntry  123 }


	gslamAGPortOspfCost OBJECT-TYPE
		SYNTAX  Integer32 (0..'FFFF'h)
		MAX-ACCESS  read-only
		STATUS  current
		DESCRIPTION
		"OSPF interface cost.  The default value of
		TOS 0 cost is 10^8/ifSpeed."
		::= { gslamAGPortEntry  124 }

	-- ************** ESOM SUPPORTS ENDS **************

        -- management port table
        gslamAGMgmtPortTable                OBJECT-TYPE
                SYNTAX          SEQUENCE OF GslamAGMgmtPortEntry
                MAX-ACCESS      not-accessible
                STATUS          current
                DESCRIPTION
                        "A table about the management port info of GSLAM-AG."
            ::= { ipiGslamAGPortObjs 2 }

        gslamAGMgmtPortEntry OBJECT-TYPE
                SYNTAX                  GslamAGMgmtPortEntry
                MAX-ACCESS      not-accessible
                STATUS                  current
                DESCRIPTION
                        "A row in the management port table.
                        Entries can't be deleted or created via SNMP ops."
		INDEX   { gslamAGShelfIndex, gslamAGIOModuleIndex, gslamAGMgmtPortIndex }
            ::= { gslamAGMgmtPortTable 1 }


        GslamAGMgmtPortEntry ::= SEQUENCE {
                gslamAGMgmtPortIndex		 Unsigned32,
                gslamAGMgmtPortIfIndex		 Unsigned32,
                gslamAGMgmtPortType		 EquipmentTypeValue,
                gslamAGMgmtPortRouting		 FlagValue,
                gslamAGMgmtPortState		 PortStateValue,
				gslamAGMgmtPortOspfAdminStatus   INTEGER,
                gslamAGMgmtPortOspfProfileId     Unsigned32,
                gslamAGMgmtPortOspfProfileName   OCTET STRING,
                gslamAGMgmtPortOspfCost      Integer32
        }

        gslamAGMgmtPortIndex        OBJECT-TYPE
                SYNTAX          Unsigned32
                MAX-ACCESS      not-accessible
                STATUS          current
                DESCRIPTION
                        "Index of GSLAM-AG management port table. It uniquely identifies
                        each port."
            ::= { gslamAGMgmtPortEntry 1 }

        gslamAGMgmtPortIfIndex      OBJECT-TYPE
                SYNTAX          Unsigned32
                MAX-ACCESS      read-only
                STATUS          current
                DESCRIPTION
                        "Indicate the ifIndex of Mib2's interface table of this
                        GSLAM-AG management port."
            ::= { gslamAGMgmtPortEntry 2 }

        gslamAGMgmtPortType         OBJECT-TYPE
                SYNTAX          EquipmentTypeValue
                MAX-ACCESS      read-write
                STATUS          current
                DESCRIPTION
                        "Indicate the equipment type of this GSLAM-AG management port."
            ::= { gslamAGMgmtPortEntry 3 }

        gslamAGMgmtPortRouting      OBJECT-TYPE
                SYNTAX          FlagValue 
                MAX-ACCESS      read-write
                STATUS          current
                DESCRIPTION
                        "Indicates point-to-point routing status of this management port.
                         Notes: This attribute cannot be modified unless the system object 
                                is in an in-service state.
                                If gslamAGMgmtPortIndex value is 1, then this attribute 
                                can only be set to 'on' if gslamAGMgmtPortState is set to 
                                'enabled'. The response genErr is returned if the previous
                                conditions are not met."
            ::= { gslamAGMgmtPortEntry 4 }

        gslamAGMgmtPortState        OBJECT-TYPE
                SYNTAX          PortStateValue 
                MAX-ACCESS      read-write
                STATUS          current
                DESCRIPTION
                        "Indicates the state of this management port.
                        Notes: This attribute cannot be modified unless the system object
                               is in an in-service state.
                               Write access to this attribute is only valid for 
                               gslamAGMgmtPortIndex value of 1. The response genErr is
                               returned if the previous conditions are not met."

            ::= { gslamAGMgmtPortEntry 5 }

    	gslamAGMgmtPortOspfAdminStatus  OBJECT-TYPE
        	SYNTAX  INTEGER { enabled (1), disabled (2) }
        	MAX-ACCESS  read-write
        	STATUS  current
        	DESCRIPTION
            	"The administrative status of OSPF on this
            	port.  The value 'enabled' denotes that OSPF
            	protocol is active on that port and 'disabled'
            	denotes that it is not."
        	DEFVAL  { 2 }       -- disabled
        	::= { gslamAGMgmtPortEntry 6 }

    	gslamAGMgmtPortOspfProfileId        OBJECT-TYPE
        	SYNTAX  Unsigned32
        	MAX-ACCESS  read-write
        	STATUS  current
        	DESCRIPTION
           	    "ID of the profile assigned to the port.
            	The corresponding profile must exist."
           DEFVAL  { 1 }       -- default profile
           ::= { gslamAGMgmtPortEntry 7 }

    	gslamAGMgmtPortOspfProfileName        OBJECT-TYPE
        	SYNTAX  OCTET STRING (SIZE (0..20))
        	MAX-ACCESS  read-write
        	STATUS  current
        	DESCRIPTION
           	    "Name of the profile assigned to the port.
            	The corresponding profile must exist."
           DEFVAL  { "Default" }       -- default profile
           ::= { gslamAGMgmtPortEntry 8 }

       gslamAGMgmtPortOspfCost OBJECT-TYPE
           SYNTAX  Integer32 (0..'FFFF'h)
           MAX-ACCESS  read-write
           STATUS  current
           DESCRIPTION
            "OSPF interface cost.  The default value of
            TOS 0 cost is 10^8/ifSpeed."
           ::= { gslamAGMgmtPortEntry 9 }

	-- UV 5.0 START

	-- port objects
	gslamAGREL50PortTable		OBJECT-TYPE
		SYNTAX		SEQUENCE OF GslamAGREL50PortEntry
		MAX-ACCESS	not-accessible
		STATUS		current
		DESCRIPTION
			"A table about the port info of GSLAM-AG."
	    ::= { ipiGslamAGPortObjs 3 }

	gslamAGREL50PortEntry OBJECT-TYPE
		SYNTAX  		GslamAGREL50PortEntry
		MAX-ACCESS	not-accessible
		STATUS  		current
		DESCRIPTION
			"A row in port table.
			Entries can't be deleted or created via SNMP ops."
		INDEX   { gslamAGREL50ShelfIndex, gslamAGREL50IOModuleIndex, gslamAGREL50PortIndex }
	    ::= { gslamAGREL50PortTable 1 }


	GslamAGREL50PortEntry ::= SEQUENCE {
		gslamAGREL50PortIndex		    Unsigned32,
		gslamAGREL50PortType			EquipmentTypeValue,
		gslamAGREL50PortAction		    ActionValue,
		gslamAGREL50PortRowStatus		RowStatus,
		gslamAGREL50PortCLEI			CLEIValue,
		gslamAGREL50PortPrimaryState	PrimaryStateValue,
		gslamAGREL50PortSecondaryState	SecondaryStateValue,
		gslamAGREL50PortWavelength		WavelengthValue, -- FREQ
		gslamAGREL50PortProtFunction		ProtectionEntityValue, -- PROTN
		gslamAGREL50PortClearDelay		Unsigned32,	-- CLRDLY
		gslamAGREL50PortDropPacket		FlagValue,	-- DROPPKT
		gslamAGREL50PortECC			    FlagValue,	-- ECC
		gslamAGREL50PortIfDirection		IfDirValue,  	-- IF
		gslamAGREL50PortLossBudget		TcvrReachValue,	-- LOSSB
		gslamAGREL50PortNDP			    FlagValue,	-- NDP
		gslamAGREL50PortSFThreshold		Unsigned32,	-- SFTH
		gslamAGREL50PortSDThreshold		Unsigned32,	-- SDTH
		gslamAGREL50PortSESThreshold		Unsigned32,	-- SESTH
		gslamAGREL50PortTxOptPower		OCTET STRING,
		gslamAGREL50PortRxOptPower		OCTET STRING,
		gslamAGREL50PortTxOptMonLev  	OCTET STRING,	-- OPRMONLEV
		gslamAGREL50PortRxOptMonLev  	OCTET STRING,   -- OPTMONLEV
		gslamAGREL50PortProtocolCap  	ProtocolCapValue, -- PROTCAP
		gslamAGREL50PortClassCap     	ClassCapValue,	-- CLASSCAP
		gslamAGREL50PortDataFieldSize    Unsigned32,	-- DATAFLDSZ
		gslamAGREL50PortSESSThreshold    Unsigned32,	-- SESSTH
		gslamAGREL50PortCSESThreshold    Unsigned32,	-- CSESTH
		gslamAGREL50PortFEC		      	FECValue,  -- FEC
		gslamAGREL50PortMedium       	MediumValue,	-- MEDIUM
		gslamAGREL50PortLineCoding   	LineCodingValue, -- LINECDE
		gslamAGREL50PortTiming       	TimingValue,	-- TMG
		gslamAGREL50PortDegMonLev    	Unsigned32,	-- DEGM
		gslamAGREL50PortDegThreshold 	Integer32,	-- DEGTHR
		gslamAGREL50PortGCC0     		FlagValue,	-- GCC0
		gslamAGREL50PortTIMDetectMode    TIMModeValue,	-- TIMDETM
		gslamAGREL50PortTIMActDisable    FlagValue,	-- TIMACTDIS
		gslamAGREL50PortExpSAPI      	OCTET STRING,	-- EXPSAPI
		gslamAGREL50PortExpDAPI      	OCTET STRING,   -- EXPDAPI
		gslamAGREL50PortExpOperSpecified  OCTET STRING,   -- EXPOPR
		gslamAGREL50PortTrcSAPI      	OCTET STRING,	-- TRCSAPI
		gslamAGREL50PortTrcDAPI      	OCTET STRING,	-- TRCDAPI
		gslamAGREL50PortTrcOperSpecified  OCTET STRING,   -- TRCOPR
		gslamAGREL50PortReceivedTrcSAPI	OCTET STRING,
		gslamAGREL50PortReceivedTrcDAPI  OCTET STRING,
		gslamAGREL50PortReceivedTrcOperSpecified  OCTET STRING,
		gslamAGREL50PortDirection    	INTEGER,	-- PDIRN
		gslamAGREL50PortHWManufactureName    HWManufactureNameValue,
		gslamAGREL50PortHWManufactureSerial  HWManufactureSerialValue,
		gslamAGREL50PortHWRevision       	HWRevisionValue,
		gslamAGREL50PortHWManufacturePartName	HWPartNumberValue,
		gslamAGREL50PortHWManufacturePartNumber      HWPartNumberValue,
		gslamAGREL50PortMuxStructure     INTEGER,
		gslamAGREL50PortCompatability	IfDirValue,
		gslamAGREL50PortAutoNegotiation	PortAutoNegotiationValue,
		gslamAGREL50PortCableType		EEPortCableTypeValue,
		gslamAGREL50PortLoopbackDuration	Unsigned32,
		gslamAGREL50PortLaserMode		LaserModeValue,
		gslamAGREL50PortSignalMapping	SignalMappingValue,
		gslamAGREL50PortLOSLevel		OCTET STRING,
		gslamAGREL50PortOSCTxPower  		OCTET STRING,   -- osc-txpower
		gslamAGREL50PortOSCRxPower  		OCTET STRING,   -- osc-rxpower
		gslamAGREL50PortOSCTxOptMonLev  	OCTET STRING,	-- osc-optmonlev
		gslamAGREL50PortOSCRxOptMonLev  	OCTET STRING,   -- osc-oprmonlev
		gslamAGREL50PortTxSpanLoss  		OCTET STRING,   -- tx span loss
		gslamAGREL50PortRxSpanLoss  		OCTET STRING,   -- rx span loss
		gslamAGREL50PortOSLRxMonLev  	OCTET STRING,   -- oslrmon-lev
		gslamAGREL50PortOSLTxMonLev  	OCTET STRING,   -- osltmon-lev
		gslamAGREL50PortActualLBC  		OCTET STRING,   -- actual-lbc
		gslamAGREL50PortLBCMonLev  		OCTET STRING,   -- lbc-monlev
		gslamAGREL50PortAttenuation		OCTET STRING,
		gslamAGREL50PortMaxFrameSize		Unsigned32,
		gslamAGREL50PortSpanLoss		FlagValue,
		gslamAGREL50PortFreqChannel		FreqChannelNumValue,
		gslamAGREL50PortLabel		OCTET STRING,
		gslamAGREL50PortVideoFrameType	INTEGER,
		gslamAGREL50PortSpeed		INTEGER,
		gslamAGREL50PortGfpOutGoingUPI	OCTET STRING,
		gslamAGREL50PortGfpIncomingUPI	OCTET STRING,
		gslamAGREL50PortGfpExpectedUPI	OCTET STRING,
		gslamAGREL50PortLOSClearLevel	OCTET STRING,
		gslamAGREL50PortOOSLaserMode		LaserModeValue,
		gslamAGREL50PortAISLAction		FlagValue,
		gslamAGREL50PortPCSCoding		PCSCoding,
		gslamAGREL50PortCktIdentifier	OCTET STRING,
		gslamAGREL50PortOptPwrCtrl INTEGER,
		gslamAGREL50PortNomTxPwr	OCTET STRING,
		gslamAGREL50PortChanSize	ChanSizeValue,
		gslamAGREL50PortOperSpeed   INTEGER,
		gslamAGREL50PortDuplexMode  DuplexMode,
        gslamAGREL50PortLpbkType    INTEGER,
                gslamAGREL50PortLOSThreshold    OCTET STRING,
                gslamAGREL50PortAddress			OCTET STRING,
		gslamAGREL50PortChannelType		INTEGER,	
		gslamAGREL50PortFlowControl		FlagValue,
		gslamAGREL50PortLaserXparency		FlagValue, 
		gslamAGREL50PortLoopTiming		FlagValue,
		gslamAGREL50PortSwitchNotification	INTEGER,
		gslamAGREL50PortSwitchDuration		INTEGER,
		gslamAGREL50PortLinkInitMode 		INTEGER,
		gslamAGREL50PortNegotiationTimer	INTEGER,
		gslamAGREL50PortLinkFailureTimer	INTEGER,
		gslamAGREL50PortSpeedNegotiation	INTEGER,
		gslamAGREL50PortCrdtMode		INTEGER,
		gslamAGREL50PortCrdtValue		INTEGER,
		gslamAGREL50PortCrdtRecoveryTimer	INTEGER,
		gslamAGREL50PortFaultNotification	INTEGER,
		gslamAGREL50PortFaultHoldOffDuration	INTEGER,
		gslamAGREL50PortTimingMode		INTEGER,
		gslamAGREL50PortECCRate			INTEGER,
		gslamAGREL50PortAssociate		INTEGER,
		gslamAGREL50PortRemoteVfptId		INTEGER,
		gslamAGREL50PortMaxUtilization		INTEGER,
		gslamAGREL50PortMinIPG			Unsigned32,
		gslamAGREL50PortLocalCondition		OCTET STRING,
		gslamAGREL50PortRemoteCondition		OCTET STRING,
		gslamAGREL50PortOspfAdminStatus 	INTEGER,
		gslamAGREL50PortOspfProfileId       Unsigned32,
		gslamAGREL50PortOspfProfileName     OCTET STRING,
		gslamAGREL50PortOspfCost        	Integer32
	}

	gslamAGREL50PortIndex	OBJECT-TYPE
		SYNTAX		Unsigned32
		MAX-ACCESS	not-accessible
		STATUS		current
		DESCRIPTION
			"Index of GSLAM-AG port table. It uniquely identifies
			each port."
	    ::= { gslamAGREL50PortEntry 1 }

	gslamAGREL50PortType	OBJECT-TYPE
		SYNTAX		EquipmentTypeValue
		MAX-ACCESS	read-write
		STATUS		current
		DESCRIPTION
			"Indicate the equipment type of this GSLAM-AG port."
	    ::= { gslamAGREL50PortEntry 2 }

	gslamAGREL50PortAction			OBJECT-TYPE
		SYNTAX		ActionValue
		MAX-ACCESS	read-write
		STATUS		current
		DESCRIPTION
			"Indicate command issued to this GSLAM-AG port."
		::= { gslamAGREL50PortEntry 3 }

	gslamAGREL50PortRowStatus		OBJECT-TYPE
		SYNTAX		RowStatus
		MAX-ACCESS	read-create
		STATUS		current
		DESCRIPTION
			"Current status of this GSLAM-AG port entry."
	    ::= { gslamAGREL50PortEntry 4 }

	gslamAGREL50PortCLEI		OBJECT-TYPE
		SYNTAX		CLEIValue
		MAX-ACCESS	read-write
		STATUS		current
		DESCRIPTION
			"Indicate the CLEI code about this GSLAM-AG port."
	::= { gslamAGREL50PortEntry 5 }

	gslamAGREL50PortPrimaryState	OBJECT-TYPE
		SYNTAX	PrimaryStateValue
 	 	MAX-ACCESS  read-write
 	 	STATUS      current
 	 	DESCRIPTION
			"Indicates the primary state of this GSLAM-AG port."
 	 	::= { gslamAGREL50PortEntry 6 }

	gslamAGREL50PortSecondaryState	OBJECT-TYPE
		SYNTAX	SecondaryStateValue
 	 	MAX-ACCESS  read-only
 	 	STATUS      current
 	 	DESCRIPTION
			"Indicates the secondary state of this GSLAM-AG port."
 	 	::= { gslamAGREL50PortEntry 7 }

	gslamAGREL50PortWavelength	OBJECT-TYPE
		SYNTAX	WavelengthValue
		MAX-ACCESS  read-only
		STATUS      current
		DESCRIPTION
			"Indicates the wavelength of this GSLAM-AG port."
		::= { gslamAGREL50PortEntry 8 }

	gslamAGREL50PortProtFunction	OBJECT-TYPE
		SYNTAX	ProtectionEntityValue
		MAX-ACCESS  read-only
		STATUS      current
		DESCRIPTION
			"Indicates the protection function of this GSLAM-AG	port."
		::= { gslamAGREL50PortEntry 9 }

	gslamAGREL50PortClearDelay	OBJECT-TYPE
		SYNTAX	Unsigned32
		MAX-ACCESS  read-write
		STATUS      current
		DESCRIPTION
			"Indicates the hysteresis time for port faults of this GSLAM-AG
			port."
		::= { gslamAGREL50PortEntry  10}

	gslamAGREL50PortDropPacket	OBJECT-TYPE
		SYNTAX	FlagValue
		MAX-ACCESS  read-write
		STATUS      current
		DESCRIPTION
			"Indicates the drop errors on transmit flag of this GSLAM-AG port."
		::= { gslamAGREL50PortEntry  11}

	gslamAGREL50PortECC	OBJECT-TYPE
		SYNTAX	FlagValue
		MAX-ACCESS  read-write
		STATUS      current
		DESCRIPTION
			"Indicates the ECC (embedded comm channel) flag of this
	    GSLAM-AG port."
		::= { gslamAGREL50PortEntry  12}

	gslamAGREL50PortIfDirection	OBJECT-TYPE
		SYNTAX	IfDirValue
		MAX-ACCESS  read-write
		STATUS      current
		DESCRIPTION
			"Indicates the interface direction of this GSLAM-AG port."
		::= { gslamAGREL50PortEntry  13}

	gslamAGREL50PortLossBudget	OBJECT-TYPE
		SYNTAX	TcvrReachValue
		MAX-ACCESS  read-only
		STATUS      current
		DESCRIPTION
			"Indicates the range of transciever in this GSLAM-AG port."
		::= { gslamAGREL50PortEntry  14}

	gslamAGREL50PortNDP	OBJECT-TYPE
		SYNTAX	FlagValue
		MAX-ACCESS  read-write
		STATUS      current
		DESCRIPTION
			"Indicates the NDP flag of this GSLAM-AG port."
		::= { gslamAGREL50PortEntry  15}

	gslamAGREL50PortSFThreshold		OBJECT-TYPE
		SYNTAX	Unsigned32
		MAX-ACCESS  read-write
		STATUS      current
		DESCRIPTION
			"Indicates the signal fail threshold value of this GSLAM-AG port."
		::= { gslamAGREL50PortEntry  16}

	 gslamAGREL50PortSDThreshold		OBJECT-TYPE
		SYNTAX	Unsigned32
		MAX-ACCESS  read-write
		STATUS      current
		DESCRIPTION
			"Indicates the signal degrade threshold value of this GSLAM-AG
			port."
		::= { gslamAGREL50PortEntry  17}

	gslamAGREL50PortSESThreshold		OBJECT-TYPE
		SYNTAX	Unsigned32
		MAX-ACCESS  read-write
		STATUS      current
		DESCRIPTION
			"Indicates the severely errored seconds declaration
				    threshold value of this GSLAM-AG port."
		::= { gslamAGREL50PortEntry  18}

	gslamAGREL50PortTxOptPower	OBJECT-TYPE
		SYNTAX		OCTET STRING(SIZE(1..15))
		MAX-ACCESS	read-only
		STATUS		current
		DESCRIPTION
			"Indicate the transmitted optical power of this
				    GSLAM-AG port."
		::= { gslamAGREL50PortEntry  19}

	gslamAGREL50PortRxOptPower	OBJECT-TYPE
		SYNTAX		OCTET STRING(SIZE(1..15))
		MAX-ACCESS	read-only
		STATUS		current
		DESCRIPTION
			"Indicate the received optical power of this GSLAM-AG port."
		::= { gslamAGREL50PortEntry  20}

    gslamAGREL50PortTxOptMonLev  OBJECT-TYPE
       	SYNTAX      OCTET STRING(SIZE(1..15))
       	MAX-ACCESS  read-write
       	STATUS      current
       	DESCRIPTION
       		"Indicate the nominal transmit optical power of this GSLAM-AG
       		port."
       	::= { gslamAGREL50PortEntry  21}

    gslamAGREL50PortRxOptMonLev  OBJECT-TYPE
       	SYNTAX      OCTET STRING(SIZE(1..15))
       	MAX-ACCESS  read-write
       	STATUS      current
       	DESCRIPTION
       		"Indicate the nominal received optical power of this GSLAM-AG
       		port."
       	::= { gslamAGREL50PortEntry  22}

	gslamAGREL50PortProtocolCap      OBJECT-TYPE
	SYNTAX  ProtocolCapValue
       	MAX-ACCESS  read-only
       	STATUS      current
       	DESCRIPTION
       		"Indicates the protocol capability of this GSLAM-AG port."
		::= { gslamAGREL50PortEntry  23}

    gslamAGREL50PortClassCap     OBJECT-TYPE
       	SYNTAX  ClassCapValue
       	MAX-ACCESS  read-only
       	STATUS      current
       	DESCRIPTION
       		"Indicates the class capability of this GSLAM-AG port."
       	::= { gslamAGREL50PortEntry  24}

    gslamAGREL50PortDataFieldSize	OBJECT-TYPE
       	SYNTAX  Unsigned32
       	MAX-ACCESS  read-only
       	STATUS      current
       	DESCRIPTION
       		"Indicates the data field size of this GSLAM-AG port."
       	::= { gslamAGREL50PortEntry  25}

    gslamAGREL50PortSESSThreshold	OBJECT-TYPE
       	SYNTAX  Unsigned32
       	MAX-ACCESS  read-write
       	STATUS      current
       	DESCRIPTION
       		"Indicates the signal errored seconds declaration
    	    threshold value of this GSLAM-AG port."
       	::= { gslamAGREL50PortEntry  26}

   	gslamAGREL50PortCSESThreshold	OBJECT-TYPE
       	SYNTAX  Unsigned32
       	MAX-ACCESS  read-write
       	STATUS      current
       	DESCRIPTION
       		"Indicates the consecutive signal errored seconds
   		    declaration threshold value of this GSLAM-AG port."
       	::= { gslamAGREL50PortEntry  27}

	gslamAGREL50PortFEC  OBJECT-TYPE
		SYNTAX  FECValue
		MAX-ACCESS  read-write
		STATUS      current
		DESCRIPTION
			"Indicates the forward error code flag of this GSLAM-AG
			port."
		::= { gslamAGREL50PortEntry  28}

    gslamAGREL50PortMedium	   OBJECT-TYPE
       	SYNTAX  MediumValue
       	MAX-ACCESS  read-only
       	STATUS      current
       	DESCRIPTION
       		"Indicates the medium type of this GSLAM-AG port."
       	::= { gslamAGREL50PortEntry  29}

   	gslamAGREL50PortLineCoding       OBJECT-TYPE
       	SYNTAX  LineCodingValue
       	MAX-ACCESS  read-only
       	STATUS      current
       	DESCRIPTION
       		"Indicates the line coding value of this GSLAM-AG port."
       	::= { gslamAGREL50PortEntry  30}

    gslamAGREL50PortTiming	   OBJECT-TYPE
       	SYNTAX  TimingValue
       	MAX-ACCESS  read-only
       	STATUS      current
       	DESCRIPTION
       		"Indicates the timing value of this GSLAM-AG port."
       	::= { gslamAGREL50PortEntry  31}

     gslamAGREL50PortDegMonLev   OBJECT-TYPE
       	SYNTAX  Unsigned32
       	MAX-ACCESS  read-write
       	STATUS      current
       	DESCRIPTION
       		"Indicates the degrade monitored level value of this
     	    GSLAM-AG port."
       	::= { gslamAGREL50PortEntry  32}

     gslamAGREL50PortDegThreshold    OBJECT-TYPE
       	SYNTAX  Integer32
       	MAX-ACCESS  read-write
       	STATUS      current
       	DESCRIPTION
       		"Indicates the degrade threshold value (percentage of
     	    errored blocks)	of this GSLAM-AG port. -1 mean not applicable"
       	::= { gslamAGREL50PortEntry  33}

    gslamAGREL50PortGCC0     OBJECT-TYPE
       	SYNTAX      FlagValue
       	MAX-ACCESS  read-write
       	STATUS      current
       	DESCRIPTION
       		"Indicate the GCC0 value of this GSLAM-AG port."
       	::= { gslamAGREL50PortEntry  34}

    gslamAGREL50PortTIMDetectMode OBJECT-TYPE
       	SYNTAX  TIMModeValue
       	MAX-ACCESS  read-write
       	STATUS      current
       	DESCRIPTION
       		"Indicates the TIM detection mode value of this GSLAM-AG port."
       	::= { gslamAGREL50PortEntry  35}

    gslamAGREL50PortTIMActDisable OBJECT-TYPE
       	SYNTAX  FlagValue
       	MAX-ACCESS  read-write
       	STATUS      current
       	DESCRIPTION
       		"Indicates the TIM consequent action value of this GSLAM-AG port."
       	::= { gslamAGREL50PortEntry  36}

    gslamAGREL50PortExpSAPI      OBJECT-TYPE
       	SYNTAX      OCTET STRING(SIZE(0..15))
       	MAX-ACCESS  read-write
       	STATUS      current
       	DESCRIPTION
       		"Indicate the expected SAPI value of this GSLAM-AG port."
	::= { gslamAGREL50PortEntry  37}

    gslamAGREL50PortExpDAPI      OBJECT-TYPE
       	SYNTAX      OCTET STRING(SIZE(0..15))
       	MAX-ACCESS  read-write
       	STATUS      current
       	DESCRIPTION
       		"Indicate the expected DAPI value of this GSLAM-AG port."
	::= { gslamAGREL50PortEntry  38}

   	gslamAGREL50PortExpOperSpecified  OBJECT-TYPE
       	SYNTAX      OCTET STRING(SIZE(0..32))
       	MAX-ACCESS  read-write
       	STATUS      current
       	DESCRIPTION
      		"Indicate the expected operator specified value of this
   		    GSLAM-AG port."
       	::= { gslamAGREL50PortEntry  39}

   	gslamAGREL50PortTrcSAPI      OBJECT-TYPE
       	SYNTAX      OCTET STRING(SIZE(0..15))
       	MAX-ACCESS  read-write
       	STATUS      current
       	DESCRIPTION
       		"Indicate the transmitted SAPI value of this GSLAM-AG port."
       	::= { gslamAGREL50PortEntry  40}

	gslamAGREL50PortTrcDAPI      OBJECT-TYPE
       	SYNTAX      OCTET STRING(SIZE(0..15))
       	MAX-ACCESS  read-write
       	STATUS      current
       	DESCRIPTION
       		"Indicate the transmitted DAPI value of this GSLAM-AG port."
	::= { gslamAGREL50PortEntry  41}

    gslamAGREL50PortTrcOperSpecified  OBJECT-TYPE
       	SYNTAX      OCTET STRING(SIZE(0..32))
       	MAX-ACCESS  read-write
       	STATUS      current
       	DESCRIPTION
       		"Indicate the transmitted operator specified value of
   		    this GSLAM-AG port."
       	::= { gslamAGREL50PortEntry  42}

    gslamAGREL50PortReceivedTrcSAPI      OBJECT-TYPE
	SYNTAX      OCTET STRING(SIZE(0..15))
	MAX-ACCESS  read-only
	STATUS      current
	DESCRIPTION
	    "Indicate the received SAPI value of this GSLAM-AG port."
	::= { gslamAGREL50PortEntry  43}

    gslamAGREL50PortReceivedTrcDAPI      OBJECT-TYPE
	SYNTAX      OCTET STRING(SIZE(0..15))
	MAX-ACCESS  read-only
	STATUS      current
	DESCRIPTION
	    "Indicate the received DAPI value of this GSLAM-AG port."
	::= { gslamAGREL50PortEntry  44}

    gslamAGREL50PortReceivedTrcOperSpecified  OBJECT-TYPE
	SYNTAX      OCTET STRING(SIZE(0..32))
	MAX-ACCESS  read-only
	STATUS      current
	DESCRIPTION
	    "Indicate the received operator specified value of this
	    GSLAM-AG port."
	::= { gslamAGREL50PortEntry  45}

    gslamAGREL50PortDirection    OBJECT-TYPE
	SYNTAX      INTEGER {
	    unknown(1),
	    not-present(2),
	    rcv(3),
	    trmt(4),
	    rcv-trmt(5),
	    uni-rcv-trmt(6)
	}
	MAX-ACCESS  read-write
	STATUS      current
	DESCRIPTION
	    "Indicates the data direction of this GSLAM-AG port."
	::= { gslamAGREL50PortEntry  46}

    gslamAGREL50PortHWManufactureName       OBJECT-TYPE
	SYNTAX      HWManufactureNameValue
	MAX-ACCESS  read-only
	STATUS      current
	DESCRIPTION
	    "Indicate hardware manufacture name about this GSLAM-AG
	    port."
	::= { gslamAGREL50PortEntry  47}

    gslamAGREL50PortHWManufactureSerial      OBJECT-TYPE
	SYNTAX      HWManufactureSerialValue
	MAX-ACCESS  read-only
	STATUS      current
	DESCRIPTION
	    "Indicate hardware manufacture serial number about this
	    GSLAM-AG port."
	::= { gslamAGREL50PortEntry  48}

    gslamAGREL50PortHWRevision       OBJECT-TYPE
	SYNTAX      HWRevisionValue
	MAX-ACCESS  read-only
	STATUS      current
	DESCRIPTION
	    "Indicate hardware revision about this GSLAM-AG port."
	::= { gslamAGREL50PortEntry  49}

    gslamAGREL50PortHWManufacturePartName	OBJECT-TYPE
	SYNTAX      HWPartNumberValue
	MAX-ACCESS  read-only
	STATUS      current
	DESCRIPTION
	    "Indicate hardware manufacture part name about this
	    GSLAM-AG port."
		::= { gslamAGREL50PortEntry 50 }

    gslamAGREL50PortHWManufacturePartNumber      OBJECT-TYPE
	SYNTAX      HWPartNumberValue
	MAX-ACCESS  read-only
	STATUS      current
	DESCRIPTION
	    "Indicate hardware manufacture part number about this
	    GSLAM-AG port."
		::= { gslamAGREL50PortEntry 51 }

    gslamAGREL50PortMuxStructure    OBJECT-TYPE
	SYNTAX      INTEGER {
	    unknown(1),
	    not-present(2),
	    channelized(3),
	    clear(4)
	}
	MAX-ACCESS  read-write
	STATUS      deprecated
	DESCRIPTION
	    "Indicates the multiplex structure for a port."
		::= { gslamAGREL50PortEntry 52 }

    gslamAGREL50PortCompatability	OBJECT-TYPE
		SYNTAX	IfDirValue
		MAX-ACCESS  read-write
		STATUS      current
		DESCRIPTION
			"Indicate whether the gbe interface can be configured as
			 network or client port during firmware upgrade. "
		::= { gslamAGREL50PortEntry 53 }

    gslamAGREL50PortAutoNegotiation	OBJECT-TYPE
		SYNTAX	PortAutoNegotiationValue
		MAX-ACCESS  read-write
		STATUS      current
		DESCRIPTION
			"Indicate whether the electrical/cu interface can be set
			 to for autonegotiation for right bandwidth. "
		::= { gslamAGREL50PortEntry 54 }

    gslamAGREL50PortCableType	OBJECT-TYPE
		SYNTAX EEPortCableTypeValue
		MAX-ACCESS  read-write
		STATUS      current
		DESCRIPTION
			"Indicate whether the 1000TBase port to swap signal pair
			 to accomodate the specified type of RJ-45 cable type
			 that is connected to the port.
			 Applicable to copper interfaces only."
		::= { gslamAGREL50PortEntry 55 }

	gslamAGREL50PortLoopbackDuration  OBJECT-TYPE
       		SYNTAX  Unsigned32
       		MAX-ACCESS  read-write
       		STATUS      current
       		DESCRIPTION
       			" This is an write only object that specifies the duration to
       			loopback. Loopback terminates after the expiry of time interval."
       		::= { gslamAGREL50PortEntry 56 }

	gslamAGREL50PortLaserMode	OBJECT-TYPE
		SYNTAX LaserModeValue
		MAX-ACCESS  read-write
		STATUS      current
		DESCRIPTION
			"Defines the laser(transmitter) bahaviour based
			 up on detection of a failure condition on the
			 incoming signal at an optical facility interface."
		::= { gslamAGREL50PortEntry 57 }

	gslamAGREL50PortSignalMapping	OBJECT-TYPE
		SYNTAX SignalMappingValue
		MAX-ACCESS  read-write
		STATUS      current
		DESCRIPTION
			"Defines the mapping for transporting the 10GbE LAN
			 client signal over OTN OTU2/OTU2e, OC-192, or STM-64 signal."
		::= { gslamAGREL50PortEntry 58 }

	gslamAGREL50PortLOSLevel	OBJECT-TYPE
		SYNTAX OCTET STRING(SIZE(1..15))
		MAX-ACCESS  read-write
		STATUS      current
		DESCRIPTION
			"Threshold for declaring the LOS defect."
		::= { gslamAGREL50PortEntry 59 }

	gslamAGREL50PortOSCTxPower	OBJECT-TYPE
		SYNTAX OCTET STRING(SIZE(1..15))
		MAX-ACCESS  read-only
		STATUS      current
		DESCRIPTION
			"OSC Tx Power"
		::= { gslamAGREL50PortEntry 60 }

	gslamAGREL50PortOSCRxPower	OBJECT-TYPE
		SYNTAX OCTET STRING(SIZE(1..15))
		MAX-ACCESS  read-only
		STATUS      current
		DESCRIPTION
			"OSC Rx Power"
		::= { gslamAGREL50PortEntry 61 }

	gslamAGREL50PortOSCTxOptMonLev	OBJECT-TYPE
		SYNTAX OCTET STRING(SIZE(1..15))
		MAX-ACCESS  read-write
		STATUS      current
		DESCRIPTION
			"Indicates nominal transmitted power on OSC "
		::= { gslamAGREL50PortEntry 62 }

	gslamAGREL50PortOSCRxOptMonLev	OBJECT-TYPE
		SYNTAX OCTET STRING(SIZE(1..15))
		MAX-ACCESS  read-write
		STATUS      current
		DESCRIPTION
			"Indicates nominal receive power on OSC "
		::= { gslamAGREL50PortEntry 63 }

	gslamAGREL50PortTxSpanLoss	OBJECT-TYPE
		SYNTAX OCTET STRING(SIZE(1..15))
		MAX-ACCESS  read-only
		STATUS      current
		DESCRIPTION
			"Tx span loss"
		::= { gslamAGREL50PortEntry 64 }

	gslamAGREL50PortRxSpanLoss	OBJECT-TYPE
		SYNTAX OCTET STRING(SIZE(1..15))
		MAX-ACCESS  read-only
		STATUS      current
		DESCRIPTION
			"Rx span loss"
		::= { gslamAGREL50PortEntry 65 }

	gslamAGREL50PortOSLRxMonLev	OBJECT-TYPE
		SYNTAX OCTET STRING(SIZE(1..15))
		MAX-ACCESS  read-write
		STATUS      current
		DESCRIPTION
			"Indicates nominal receive span loss power"
		::= { gslamAGREL50PortEntry 66 }

	gslamAGREL50PortOSLTxMonLev	OBJECT-TYPE
		SYNTAX OCTET STRING(SIZE(1..15))
		MAX-ACCESS  read-write
		STATUS      current
		DESCRIPTION
			"Indicates nominal tramit span loss power"
		::= { gslamAGREL50PortEntry 67 }

	gslamAGREL50PortActualLBC	OBJECT-TYPE
		SYNTAX OCTET STRING(SIZE(1..15))
		MAX-ACCESS  read-only
		STATUS      current
		DESCRIPTION
			"Actual Laser Bias Current value."
		::= { gslamAGREL50PortEntry 68 }

	gslamAGREL50PortLBCMonLev	OBJECT-TYPE
		SYNTAX OCTET STRING(SIZE(1..15))
		MAX-ACCESS  read-only  -- write ??
		STATUS      current
		DESCRIPTION
			"Indicated nominal Laser Bias Current value."
		::= { gslamAGREL50PortEntry 69 }

	gslamAGREL50PortAttenuation	OBJECT-TYPE
		SYNTAX OCTET STRING(SIZE(1..15))
		MAX-ACCESS  read-write
		STATUS      current
		DESCRIPTION
			"Used to add attenuation in order to adjust power
			 for individual optical channels."
		::= { gslamAGREL50PortEntry 70 }

    	gslamAGREL50PortMaxFrameSize	OBJECT-TYPE
       		SYNTAX  Unsigned32
       		MAX-ACCESS  read-write
       		STATUS      current
       		DESCRIPTION
       			"Indicates max frame size that can be sent over the interface."
       		::= { gslamAGREL50PortEntry 71 }

	gslamAGREL50PortSpanLoss      OBJECT-TYPE
		SYNTAX      FlagValue
		MAX-ACCESS  read-write
		STATUS      current
		DESCRIPTION
			"Indicates enable/disable the automatic gain adjustment of
			 the amplifier to offset the loss of previous transmission
			 fiber."
		::= { gslamAGREL50PortEntry 72 }

	gslamAGREL50PortFreqChannel      OBJECT-TYPE
		SYNTAX      FreqChannelNumValue
		MAX-ACCESS  read-write
		STATUS      current
		DESCRIPTION
			"Indicates frequency or channel number for tunable port."
		::= { gslamAGREL50PortEntry 73 }

	gslamAGREL50PortLabel	OBJECT-TYPE
		SYNTAX OCTET STRING(SIZE(1..32))
		MAX-ACCESS  read-only
		STATUS      current
		DESCRIPTION
			"Catalog label to uniquely identify and AID."
		::= { gslamAGREL50PortEntry 74 }

	gslamAGREL50PortVideoFrameType    OBJECT-TYPE
		SYNTAX      INTEGER {
	    		unknown (1),
	    		not-present (2),
	    		lines-525 (3),
	    		lines-625 (4)
		}
		MAX-ACCESS  read-write
		STATUS      current
		DESCRIPTION
	    	"Indicates the frame format of the component video in serial digital D1 video signal."
		::= { gslamAGREL50PortEntry 75 }

	gslamAGREL50PortSpeed    OBJECT-TYPE
		SYNTAX      INTEGER {
	    		unknown (1),
	    		not-present (2),
	    		mbps-10 (3),
	    		mbps-100 (4),
	    		gbps-1(5),
	    		gbps-10(6)
		}
		MAX-ACCESS  read-write
		STATUS      current
		DESCRIPTION
	    	"Indicates speed on 10/100Base-T Ethernet interface"
		::= { gslamAGREL50PortEntry 76 }

	gslamAGREL50PortGfpOutGoingUPI OBJECT-TYPE
		SYNTAX OCTET STRING(SIZE(1..20))
		MAX-ACCESS  read-only
		STATUS      current
		DESCRIPTION
			"Out going User Payload Identifier(UPI) value in payload
			 header of GFP-T/GFP-F framed client signal"
		::= { gslamAGREL50PortEntry 77 }

	gslamAGREL50PortGfpExpectedUPI	OBJECT-TYPE
		SYNTAX OCTET STRING(SIZE(1..20))
		MAX-ACCESS  read-only
		STATUS      current
		DESCRIPTION
			"Expected User Payload Identifier(UPI) value in payload
			 header of GFP-T/GFP-F framed client signal"
		::= { gslamAGREL50PortEntry 78 }

	gslamAGREL50PortGfpIncomingUPI OBJECT-TYPE
		SYNTAX OCTET STRING(SIZE(1..20))
		MAX-ACCESS  read-only
		STATUS      current
		DESCRIPTION
			"Incoming User Payload Identifier(UPI) value in payload
			 header of GFP-T/GFP-F framed client signal"
		::= { gslamAGREL50PortEntry 79 }

	gslamAGREL50PortLOSClearLevel	OBJECT-TYPE
		SYNTAX OCTET STRING(SIZE(1..15))
		MAX-ACCESS  read-write
		STATUS      current
		DESCRIPTION
			"Threshold for clearing the LOS defect."
		::= { gslamAGREL50PortEntry 80 }

	gslamAGREL50PortOOSLaserMode	OBJECT-TYPE
		SYNTAX LaserModeValue
		MAX-ACCESS  read-write
		STATUS      current
		DESCRIPTION
			"Defines the laser(transmitter) bahaviour for an
			 optical facility interface in OOS state."
		::= { gslamAGREL50PortEntry 81 }

	gslamAGREL50PortAISLAction	OBJECT-TYPE
		SYNTAX      FlagValue
		MAX-ACCESS  read-write
		STATUS      current
		DESCRIPTION
			"Indicates the consequence action when port in ais-l"
	::= { gslamAGREL50PortEntry 82 }

	gslamAGREL50PortPCSCoding	OBJECT-TYPE
		SYNTAX      PCSCoding
		MAX-ACCESS  read-write
		STATUS      current
		DESCRIPTION
			"Indicates the behavior of PCS layer at an
			 FC1200 Fiber Channel facility interface"
	::= { gslamAGREL50PortEntry 83 }

	gslamAGREL50PortCktIdentifier    OBJECT-TYPE
    	SYNTAX  	OCTET STRING(SIZE(1..20))
    	MAX-ACCESS  read-write
   	    STATUS      current
    	DESCRIPTION
     	"A ckt identifier for an OCH port. 
			This consists of up to 62 7-bit ASCII characters."
  	::= {gslamAGREL50PortEntry 84}

	gslamAGREL50PortOptPwrCtrl    OBJECT-TYPE
      	SYNTAX  INTEGER {
         	 unknown(1),
           	 manual(2),
           	 auto(3),
           	 not-applicable(4)
		}
    	MAX-ACCESS  read-write
   		STATUS      current
    	DESCRIPTION
    		 "This is a flag with value MAN|AUTO for OTS/OPS ports.
				For non-ots/ops ports this value will be (4)"
   	::= {gslamAGREL50PortEntry 85}

	gslamAGREL50PortNomTxPwr    OBJECT-TYPE
		SYNTAX 	OCTET STRING(SIZE(1..15))
    	MAX-ACCESS  read-write
   		STATUS      current
    	DESCRIPTION
        	"The nominal transmit power of OTS/OPS/OCG port"
   	::= {gslamAGREL50PortEntry 86}

	gslamAGREL50PortChanSize	OBJECT-TYPE
		SYNTAX		ChanSizeValue
    	MAX-ACCESS  read-write
		STATUS		current
		DESCRIPTION
			"OTNCG port channel size."
	    ::= { gslamAGREL50PortEntry 87 }
    
	gslamAGREL50PortOperSpeed		OBJECT-TYPE
		SYNTAX      INTEGER {
	    		unknown (1),
	    		not-present (2),
	    		mbps-10 (3),
	    		mbps-100 (4),
	    		gbps-1 (5),
	    		gbps-10 (6)
		}
		MAX-ACCESS  read-only
		STATUS      current
		DESCRIPTION
	    	"Indicates speed on 10/100/1000 Ethernet interface"
		::= { gslamAGREL50PortEntry 88 }

				
	gslamAGREL50PortDuplexMode	OBJECT-TYPE
		SYNTAX      DuplexMode
		MAX-ACCESS  read-only
		STATUS      current
		DESCRIPTION
			"full-duplex or half-duplex"
		::= { gslamAGREL50PortEntry 89 }

    gslamAGREL50PortLpbkType        OBJECT-TYPE
        SYNTAX      INTEGER {
                unknown (1),
                not-present (2),
                facility (3),
                terminal (4) 
        }
        MAX-ACCESS  read-only
        STATUS      current
        DESCRIPTION
            "Indicates loopback type on a port"
        ::= { gslamAGREL50PortEntry 90 }

        gslamAGREL50PortLOSThreshold     OBJECT-TYPE
                SYNTAX  OCTET STRING(SIZE(1..8))
                MAX-ACCESS      read-only
                STATUS    current
                DESCRIPTION
                    "LOS threshold value for Raman module in dB "
                ::= { gslamAGREL50PortEntry 91 }
 	
	-- ************** ESOM SUPPORT STARTS **************
  	gslamAGREL50PortAddress      OBJECT-TYPE
		SYNTAX          OCTET STRING (SIZE(0..31))
		MAX-ACCESS      read-only
		STATUS          current
		DESCRIPTION
			"Indicate the MAC address of ESOM Card Module"
		::= { gslamAGREL50PortEntry  92}

	gslamAGREL50PortChannelType      OBJECT-TYPE
		SYNTAX		INTEGER {
					unknown(1),
					not-applicable(2),
					opvcx(3),
					vptch(4)
				} 
		MAX-ACCESS      read-write
		STATUS          current
		DESCRIPTION
			"Indicate the channel type of client port (opvcx | vptch)"
		::= { gslamAGREL50PortEntry  93}	

	
	gslamAGREL50PortFlowControl	OBJECT-TYPE
		SYNTAX          FlagValue 
		MAX-ACCESS      read-write
		STATUS          current
		DESCRIPTION
			"Indicate the flow control state of the port."
		::= { gslamAGREL50PortEntry  94}

	gslamAGREL50PortLaserXparency	OBJECT-TYPE
		SYNTAX          FlagValue
		MAX-ACCESS      read-write
		STATUS          current
		DESCRIPTION
			"Indicate the laser transparency state of the port."
		::= { gslamAGREL50PortEntry  95}

	gslamAGREL50PortLoopTiming 	OBJECT-TYPE
			SYNTAX       	FlagValue
			MAX-ACCESS      read-write
			STATUS          current
			DESCRIPTION
				"Indicate the loop-timing mode for the selected SONET/SDH interface"
		::= { gslamAGREL50PortEntry  96}
	
	gslamAGREL50PortSwitchNotification 	OBJECT-TYPE
			SYNTAX          INTEGER {
						not-applicable(1),
						disabled(2),
						nos(3),
						lr(4),
						ud(5),
						breakLink(6),
						linkFail(7),
						laserWink(8)
						} 
			MAX-ACCESS      read-write
			STATUS          current
			DESCRIPTION
				"Indicate the Switch Notification state of the port."
		::= { gslamAGREL50PortEntry  97}
		
	gslamAGREL50PortSwitchDuration	OBJECT-TYPE
		SYNTAX          INTEGER(100..5000)
		MAX-ACCESS      read-write
		STATUS          current
		DESCRIPTION
	       "Indicate the duration with in which protection switch should occur across the port"
		::= { gslamAGREL50PortEntry  98}
		
	gslamAGREL50PortLinkInitMode 	OBJECT-TYPE
		SYNTAX          INTEGER {
				not-applicable(1),
				transparent(2), 
				semi-transparent(3), 
				local(4)
				}	
		MAX-ACCESS      read-write
		STATUS          current
		DESCRIPTION
			"Indicate the link initialization state of the port."
		::= { gslamAGREL50PortEntry  99}
	
	gslamAGREL50PortNegotiationTimer 	OBJECT-TYPE
		SYNTAX          INTEGER (10..20)
		MAX-ACCESS      read-write
		STATUS          current
		DESCRIPTION
		       "Indicate the GbE Auto Negotiation Link Timer in ms."
		::= { gslamAGREL50PortEntry  100}

	gslamAGREL50PortLinkFailureTimer	OBJECT-TYPE
		SYNTAX          INTEGER (0..200)
		MAX-ACCESS      read-write
		STATUS          current
		DESCRIPTION
		       "Indicate the breaklink detection persistence timer of GbE port in ms."
		::= { gslamAGREL50PortEntry  101}

	gslamAGREL50PortSpeedNegotiation	OBJECT-TYPE
		SYNTAX          INTEGER {
					not-applicable(1),
					auto(2),
					fc-1G(3), 
					fc-2G(4), 
					fc-4G(5)  
				}
		MAX-ACCESS      read-write
		STATUS          current
		DESCRIPTION
		       "Indicate the Gigabit Fiber Channel speed negotiation line rate of the port."
		::= { gslamAGREL50PortEntry  102}
	
	gslamAGREL50PortCrdtMode 	OBJECT-TYPE
		SYNTAX          INTEGER {
			not-applicable(1),
			auto(2), 
			manual(3)
			}
		MAX-ACCESS      read-write
		STATUS          current
		DESCRIPTION
			"Configure the GbFC buffer credit settings for FCHP port."
		::= { gslamAGREL50PortEntry  103}

	gslamAGREL50PortCrdtValue 	OBJECT-TYPE
		SYNTAX          INTEGER (1..255)
		MAX-ACCESS      read-write
		STATUS          current
		DESCRIPTION
			"Indicates CTx buffer to buffer credit value"
		::= { gslamAGREL50PortEntry  104}
	
	gslamAGREL50PortCrdtRecoveryTimer 	OBJECT-TYPE
		SYNTAX          INTEGER (0..25000)
		MAX-ACCESS      read-write
		STATUS          current
		DESCRIPTION
			"Indicates the credit starvation recovery timer"
		::= { gslamAGREL50PortEntry  105}
	
	gslamAGREL50PortFaultNotification 	OBJECT-TYPE
		SYNTAX          INTEGER{
				not-applicable(1),
				disabled(2),
				nos(3), 
				ols(4), 
				breakLink(5), 
				linkFail(6), 
				linkOffLine(7),
				laserDisable(8)
		}
		MAX-ACCESS      read-write
		STATUS          current
		DESCRIPTION
	       "Indicate "
		::= { gslamAGREL50PortEntry  106}

	gslamAGREL50PortFaultHoldOffDuration 	OBJECT-TYPE
		SYNTAX          INTEGER(0..200)
		MAX-ACCESS      read-write
		STATUS          current
		DESCRIPTION
	       "Indicate the hold off duration for fault on port to get cleared"
		::= { gslamAGREL50PortEntry  107}
	
	gslamAGREL50PortTimingMode 	OBJECT-TYPE
		SYNTAX          INTEGER {
			not-applicable(1),
			self-timed(2), 
			loop-timed(3),
			freerun(4)
			}
		MAX-ACCESS      read-only
		STATUS          current
		DESCRIPTION
			"Indicate the Active Timing mode of the port."
		::= { gslamAGREL50PortEntry  108}
	
	gslamAGREL50PortECCRate 	OBJECT-TYPE
		SYNTAX		INTEGER {
				not-applicable(1),
				ibcc-64(2),
				ibcc-128(3),
				ibcc-192(4),
				ibcc-256(5),
				ibcc-320(6),
				ibcc-384(7),
				ibcc-448(8),
				ibcc-512(9),
				ibcc-576(10),
				ibcc-640(11),
				ibcc-704(12),
				ibcc-768(13),
				ibcc-832(14),
				ibcc-896(15),
				ibcc-960(16)
			}
		MAX-ACCESS      read-write
		STATUS          current
		DESCRIPTION
			"Indicate the maximum aggregated rate of the Embedded Communication Channels carried over the IBCC of the VFNT in context."
		::= { gslamAGREL50PortEntry  109}

	gslamAGREL50PortAssociate 	OBJECT-TYPE
		SYNTAX          INTEGER {
			not-applicable(1),
			otncg(2), 
			stncg(3),
			ptnrg(4)
			}
		MAX-ACCESS      read-write
		STATUS          current
		DESCRIPTION
			"Indicate the associated network channel terminating entity to VFNT interface"
	::= { gslamAGREL50PortEntry  110}
	
	gslamAGREL50PortRemoteVfptId	OBJECT-TYPE
		SYNTAX          INTEGER(1..12)
		MAX-ACCESS      read-write
		STATUS          current
		DESCRIPTION
	       "Indicate the the remote VFPT identifier provisioned against the local VFPT"
		::= { gslamAGREL50PortEntry  111 }
		
	gslamAGREL50PortMaxUtilization 	OBJECT-TYPE
		SYNTAX          INTEGER(1..100)
		MAX-ACCESS      read-write
		STATUS          current
		DESCRIPTION
	       "Indicate the maximum egress utilization permitted on the ethernet interface, as a percentage of the gigabit ethernet nominal rate from 1% to 100%"
		::= { gslamAGREL50PortEntry  112 }
	
	gslamAGREL50PortMinIPG	OBJECT-TYPE
		SYNTAX          Unsigned32	
		MAX-ACCESS      read-write
		STATUS          current
		DESCRIPTION
	       "Indicate the minimum IPG permitted to be transmitted on the ethernet interface, in ns from 96ns to 1008ns of the port"
		::= { gslamAGREL50PortEntry  113}

	gslamAGREL50PortLocalCondition	OBJECT-TYPE
			SYNTAX          OCTET STRING (SIZE(0..31))
			MAX-ACCESS      read-only
			STATUS          current
			DESCRIPTION
			"Indicate the Local Fault Condition of the ESOM Port"
			::= { gslamAGREL50PortEntry  114}
			
	gslamAGREL50PortRemoteCondition	OBJECT-TYPE
			SYNTAX          OCTET STRING (SIZE(0..31))
			MAX-ACCESS      read-only
			STATUS          current
			DESCRIPTION
			"Indicate the Remote Fault Condition of the ESOM Port"
		::= { gslamAGREL50PortEntry  115}
		
	gslamAGREL50PortOspfAdminStatus OBJECT-TYPE
		SYNTAX  INTEGER { enabled (1), disabled (2) }
		MAX-ACCESS  read-write
		STATUS  current
		DESCRIPTION
		"The administrative status of OSPF on this
		port.  The value 'enabled' denotes that OSPF
		protocol is active on that port and 'disabled'
		denotes that it is not."
		DEFVAL  { 2 }       -- disabled
		::= { gslamAGREL50PortEntry  126 }

	gslamAGREL50PortOspfProfileId       OBJECT-TYPE
		SYNTAX  Unsigned32
		MAX-ACCESS  read-write
		STATUS  current
		DESCRIPTION
		"ID of the profile assigned to the port.
		The corresponding profile must exist."
		DEFVAL  { 1 }       -- default profile
		::= { gslamAGREL50PortEntry  127 }

	gslamAGREL50PortOspfProfileName       OBJECT-TYPE
		SYNTAX  OCTET STRING (SIZE (0..20))
		MAX-ACCESS  read-write
		STATUS  current
		DESCRIPTION
		"Name of the profile assigned to the port.
		The corresponding profile must exist."
		DEFVAL  { "Default" }       -- default profile
		::= { gslamAGREL50PortEntry  128 }

	gslamAGREL50PortOspfCost    OBJECT-TYPE
		SYNTAX  Integer32 (0..'FFFF'h)
		MAX-ACCESS  read-only
		STATUS  current
		DESCRIPTION
		"OSPF interface cost.  The default value of
		TOS 0 cost is 10^8/ifSpeed."
		::= { gslamAGREL50PortEntry  129 }

	-- ************** ESOM SUPPORTS ENDS **************

 -- Subtending up-port table
    gslamAGUPPortTable                OBJECT-TYPE
        SYNTAX          SEQUENCE OF GslamAGUPPortEntry
        MAX-ACCESS      not-accessible
        STATUS          current
        DESCRIPTION
             "A table about the Subtending port info of GSLAM-AG."
        ::= { ipiGslamAGPortObjs 4 }

    gslamAGUPPortEntry OBJECT-TYPE
        SYNTAX                  GslamAGUPPortEntry
        MAX-ACCESS      not-accessible
        STATUS          current
        DESCRIPTION
             "A row in the Subtending port table.
              Entries can't be deleted or created via SNMP ops."
        INDEX   { gslamAGREL50ShelfIndex, gslamAGUPPortIndex }
        ::= { gslamAGUPPortTable 1 }

    GslamAGUPPortEntry ::= SEQUENCE {
        gslamAGUPPortIndex       Unsigned32
    }

    gslamAGUPPortIndex  OBJECT-TYPE
        SYNTAX      Unsigned32
        MAX-ACCESS  read-only 
        STATUS      current
        DESCRIPTION
            "Indicates the port index for an Subtending"
    ::= { gslamAGUPPortEntry 1 }

 -- Subtending-down port table
    gslamAGDOWNPortTable                OBJECT-TYPE
        SYNTAX          SEQUENCE OF GslamAGDOWNPortEntry
        MAX-ACCESS      not-accessible
        STATUS          current
        DESCRIPTION
             "A table about the Subtending port info of GSLAM-AG."
        ::= { ipiGslamAGPortObjs 5 }

    gslamAGDOWNPortEntry OBJECT-TYPE
        SYNTAX                  GslamAGDOWNPortEntry
        MAX-ACCESS      not-accessible
        STATUS          current
        DESCRIPTION
             "A row in the Subtending port table.
              Entries can't be deleted or created via SNMP ops."
        INDEX   { gslamAGREL50ShelfIndex, gslamAGDOWNPortIndex }
        ::= { gslamAGDOWNPortTable 1 }

    GslamAGDOWNPortEntry ::= SEQUENCE {
        gslamAGDOWNPortIndex         Unsigned32
    }

    gslamAGDOWNPortIndex    OBJECT-TYPE
        SYNTAX      Unsigned32
        MAX-ACCESS  read-only 
        STATUS      current
        DESCRIPTION
            "Indicates the port index for an Subtending"
    ::= { gslamAGDOWNPortEntry 1 }

	-- UV 5.0 END

	-- channel objects
	gslamAGChannelTable		OBJECT-TYPE
		SYNTAX		SEQUENCE OF GslamAGChannelEntry
		MAX-ACCESS	not-accessible
		STATUS		current
		DESCRIPTION
			"A table about the channel info of GSLAM-AG."
	    ::= { ipiGslamAGChannelObjs 1 }

	gslamAGChannelEntry OBJECT-TYPE
		SYNTAX  		GslamAGChannelEntry
		MAX-ACCESS	not-accessible
		STATUS  		current
		DESCRIPTION
			"A row in channel table.
			Entries can't be deleted or created via SNMP ops."
		INDEX   { gslamAGShelfIndex, gslamAGIOModuleIndex, gslamAGPortIndex, gslamAGChannelIndex }
	    ::= { gslamAGChannelTable 1 }


	GslamAGChannelEntry ::= SEQUENCE {
		gslamAGChannelIndex		Unsigned32,
		gslamAGChannelIfIndex	Unsigned32,
		gslamAGChannelType		EquipmentTypeValue,
		gslamAGChannelAction		ActionValue,
		gslamAGChannelPrimaryState	PrimaryStateValue,
		gslamAGChannelSecondaryState	SecondaryStateValue,
		gslamAGChannelProtFunction	ProtectionEntityValue,
		gslamAGChannelExpTrc		OCTET STRING,   -- EXPTRC
		gslamAGChannelTrc		    OCTET STRING,   -- TRC
		gslamAGChannelReceivedTrc	OCTET STRING,	-- INCTRC
		gslamAGChannelSFThreshold	Unsigned32,     -- SFTH
		gslamAGChannelSDThreshold	Unsigned32,     -- SDTH
		gslamAGChannelSESThreshold	Unsigned32,     -- SESTH
		gslamAGChannelCSESThreshold Unsigned32, 	-- CSESTH
		gslamAGChannelDegMonLev 	Unsigned32,     -- DEGM
		gslamAGChannelDegThreshold  Integer32,	    -- DEGTHR
		gslamAGChannelOCIProtSwitch FlagValue,	    -- OCIPS
		gslamAGChannelTIMDetectMode TIMModeValue,   -- TIMDETM
		gslamAGChannelTIMActDisable FlagValue,	-- TIMACTDIS
		gslamAGChannelExpSAPI   	OCTET STRING,	-- EXPSAPI
		gslamAGChannelExpDAPI   	OCTET STRING,   -- EXPDAPI
		gslamAGChannelExpOperSpecified   OCTET STRING,   -- EXPOPR
		gslamAGChannelTrcSAPI   	OCTET STRING,	-- TRCSAPI
		gslamAGChannelTrcDAPI   	OCTET STRING,   -- TRCDAPI
		gslamAGChannelTrcOperSpecified   OCTET STRING,   -- TRCOPR
		gslamAGChannelReceivedTrcSAPI   OCTET STRING,
		gslamAGChannelReceivedTrcDAPI   OCTET STRING,
		gslamAGChannelReceivedTrcOperSpecified   OCTET STRING,
		gslamAGChannelMuxStructure	INTEGER,
		gslamAGChannelDEGAction		FlagValue,
        gslamAGChannelCRSLpbkType       INTEGER,
        gslamAGChannelCRSLpbkDuration   Unsigned32,
        gslamAGChannelShapingState		FlagValue,
		gslamAGChannelShapingRate		INTEGER,
		gslamAGChannelLocalExtn		INTEGER,
		gslamAGChannelNwExtn		INTEGER,
		gslamAGChannelCompression	FlagValue,
		gslamAGChannelNDP		FlagValue,
		gslamAGChannelOSPF		FlagValue,
		gslamAGChannelGroupSize		INTEGER
	}

	gslamAGChannelIndex	OBJECT-TYPE
		SYNTAX		Unsigned32
		MAX-ACCESS	not-accessible
		STATUS		current
		DESCRIPTION
			"Index of GSLAM-AG channel table. It uniquely identifies
			each channel."
    	::= { gslamAGChannelEntry 1 }

	gslamAGChannelIfIndex	OBJECT-TYPE
		SYNTAX		Unsigned32
		MAX-ACCESS	read-only
		STATUS		current
		DESCRIPTION
			"Indicate the ifIndex of Mib2's interface table of this
			GSLAM-AG channel."
	    ::= { gslamAGChannelEntry 2 }

	gslamAGChannelType	OBJECT-TYPE
		SYNTAX		EquipmentTypeValue
		MAX-ACCESS	read-only
		STATUS		current
		DESCRIPTION
			"Indicate the equipment type of this GSLAM-AG channel."
	    ::= { gslamAGChannelEntry 3 }

    gslamAGChannelAction     OBJECT-TYPE
	SYNTAX      ActionValue
	MAX-ACCESS  read-write
	STATUS      current
	DESCRIPTION
	    "Indicate command issued to this GSLAM-AG channel."
	::= { gslamAGChannelEntry 4 }

	gslamAGChannelPrimaryState	OBJECT-TYPE
		SYNTAX	PrimaryStateValue
 	 	MAX-ACCESS  read-only
 	 	STATUS      current
 	 	DESCRIPTION
			"Indicates the primary state of this GSLAM-AG channel."
 	 	::= { gslamAGChannelEntry 5 }

	gslamAGChannelSecondaryState	OBJECT-TYPE
		SYNTAX	SecondaryStateValue
 	 	MAX-ACCESS  read-only
 	 	STATUS      current
 	 	DESCRIPTION
		    "Indicates the secondary state of this GSLAM-AG channel."
 	 	::= { gslamAGChannelEntry 6 }

	gslamAGChannelProtFunction	OBJECT-TYPE
		SYNTAX	ProtectionEntityValue
		MAX-ACCESS  read-only
		STATUS      current
		DESCRIPTION
			"Indicates the protection function of this GSLAM-AG channel."
		::= { gslamAGChannelEntry 7 }

    gslamAGChannelExpTrc		OBJECT-TYPE
		SYNTAX		OCTET STRING(SIZE(0..64))
		MAX-ACCESS	read-write
		STATUS		current
		DESCRIPTION
			"Indicates the expected trace value of the GSLAM-AG channel."
		::= { gslamAGChannelEntry 8 }

	gslamAGChannelTrc		OBJECT-TYPE
		SYNTAX		OCTET STRING(SIZE(0..64))
		MAX-ACCESS	read-write
		STATUS		current
		DESCRIPTION
			"Indicates the transmitted trace value of the GSLAM-AG
			channel."
		::= { gslamAGChannelEntry 9 }

	gslamAGChannelReceivedTrc     OBJECT-TYPE
	SYNTAX      OCTET STRING(SIZE(0..64))
	MAX-ACCESS  read-only
	STATUS      current
	DESCRIPTION
	    "Indicates the received trace value of the GSLAM-AG
	    channel."
	::= { gslamAGChannelEntry 10 }

    gslamAGChannelSFThreshold		OBJECT-TYPE
		SYNTAX	Unsigned32
		MAX-ACCESS  read-write
		STATUS      current
		DESCRIPTION
			"Indicates the signal fail threshold value of this
			GSLAM-AG channel."
		::= { gslamAGChannelEntry 11 }

    gslamAGChannelSDThreshold		OBJECT-TYPE
		SYNTAX	Unsigned32
		MAX-ACCESS  read-write
		STATUS      current
		DESCRIPTION
		    "Indicates the signal degrade threshold value of this
			GSLAM-AG channel."
		::= { gslamAGChannelEntry 12 }

	gslamAGChannelSESThreshold		OBJECT-TYPE
		SYNTAX	Unsigned32
		MAX-ACCESS  read-write
		STATUS      current
		DESCRIPTION
			"Indicates the severely errored seconds declaration
			threshold value of this GSLAM-AG channel."
	    ::= { gslamAGChannelEntry 13 }

    gslamAGChannelCSESThreshold     OBJECT-TYPE
	SYNTAX  Unsigned32
	MAX-ACCESS  read-write
	STATUS      current
	DESCRIPTION
	    "Indicates the consecutive signal errored seconds
	    declaration threshold value of this GSLAM-AG channel."
	::= { gslamAGChannelEntry 14 }

    gslamAGChannelDegMonLev OBJECT-TYPE
	SYNTAX  Unsigned32
	MAX-ACCESS  read-write
	STATUS      current
	DESCRIPTION
	    "Indicates the degrade monitored level value of this
	    GSLAM-AG channel."
	::= { gslamAGChannelEntry 15 }

    gslamAGChannelDegThreshold  OBJECT-TYPE
	SYNTAX  Integer32
	MAX-ACCESS  read-write
	STATUS      current
	DESCRIPTION
	    "Indicates the degrade threshold value (percentage of
	    errored blocks) of this GSLAM-AG channel. -1 mean not applicable"
	::= { gslamAGChannelEntry 16 }

    gslamAGChannelOCIProtSwitch OBJECT-TYPE
	SYNTAX  FlagValue
	MAX-ACCESS  read-write
	STATUS      current
	DESCRIPTION
	    "Indicates the OCI consequent action value of this
	    GSLAM-AG channel."
	::= { gslamAGChannelEntry 17 }

    gslamAGChannelTIMDetectMode OBJECT-TYPE
	SYNTAX  TIMModeValue
	MAX-ACCESS  read-write
	STATUS      current
	DESCRIPTION
	    "Indicates the TIM detection mode value of this
	    GSLAM-AG channel."
	::= { gslamAGChannelEntry 18 }

    gslamAGChannelTIMActDisable OBJECT-TYPE
	SYNTAX  FlagValue
	MAX-ACCESS  read-write
	STATUS      current
	DESCRIPTION
	    "Indicates the TIM consequent action value of this
	    GSLAM-AG channel."
	::= { gslamAGChannelEntry 19 }

    gslamAGChannelExpSAPI   OBJECT-TYPE
	SYNTAX      OCTET STRING(SIZE(0..15))
	MAX-ACCESS  read-write
	STATUS      current
	DESCRIPTION
	    "Indicate the expected SAPI value of this GSLAM-AG
	    channel."
	::= { gslamAGChannelEntry 20 }

    gslamAGChannelExpDAPI   OBJECT-TYPE
	SYNTAX      OCTET STRING(SIZE(0..15))
	MAX-ACCESS  read-write
	STATUS      current
	DESCRIPTION
	    "Indicate the expected DAPI value of this GSLAM-AG
	    channel."
	::= { gslamAGChannelEntry 21 }

    gslamAGChannelExpOperSpecified   OBJECT-TYPE
	SYNTAX      OCTET STRING(SIZE(0..32))
	MAX-ACCESS  read-write
	STATUS      current
	DESCRIPTION
	    "Indicate the expected operator specified value of this
	    GSLAM-AG channel."
	::= { gslamAGChannelEntry 22 }

    gslamAGChannelTrcSAPI   OBJECT-TYPE
	SYNTAX      OCTET STRING(SIZE(0..15))
	MAX-ACCESS  read-write
	STATUS      current
	DESCRIPTION
	    "Indicate the transmitted SAPI value of this GSLAM-AG
	    channel."
	::= { gslamAGChannelEntry 23 }

    gslamAGChannelTrcDAPI   OBJECT-TYPE
	SYNTAX      OCTET STRING(SIZE(0..15))
	MAX-ACCESS  read-write
	STATUS      current
	DESCRIPTION
	    "Indicate the transmitted DAPI value of this GSLAM-AG
	    channel."
	::= { gslamAGChannelEntry 24 }

    gslamAGChannelTrcOperSpecified   OBJECT-TYPE
	SYNTAX      OCTET STRING(SIZE(0..32))
	MAX-ACCESS  read-write
	STATUS      current
	DESCRIPTION
	    "Indicate the transmitted operator specified value of
	    this GSLAM-AG channel."
	::= { gslamAGChannelEntry 25 }

    gslamAGChannelReceivedTrcSAPI   OBJECT-TYPE
	SYNTAX      OCTET STRING(SIZE(0..15))
	MAX-ACCESS  read-only
	STATUS      current
	DESCRIPTION
	    "Indicate the received SAPI value of this GSLAM-AG
	    channel."
	::= { gslamAGChannelEntry 26 }

    gslamAGChannelReceivedTrcDAPI   OBJECT-TYPE
	SYNTAX      OCTET STRING(SIZE(0..15))
	MAX-ACCESS  read-only
	STATUS      current
	DESCRIPTION
	    "Indicate the received DAPI value of this GSLAM-AG
	    channel."
	::= { gslamAGChannelEntry 27 }

    gslamAGChannelReceivedTrcOperSpecified   OBJECT-TYPE
	SYNTAX      OCTET STRING(SIZE(0..32))
	MAX-ACCESS  read-only
	STATUS      current
	DESCRIPTION
	    "Indicate the received operator specified value of
	    this GSLAM-AG channel."
	::= { gslamAGChannelEntry 28 }

    gslamAGChannelMuxStructure    OBJECT-TYPE
	SYNTAX      INTEGER {
	    unknown(1),
	    not-present(2),
	    channelized(3),
	    clear(4)
	}
	MAX-ACCESS  read-write
	STATUS      current
	DESCRIPTION
	    "Indicates the multiplex structure for an ODUk channel."
	::= { gslamAGChannelEntry 29 }

    gslamAGChannelDEGAction		OBJECT-TYPE
	SYNTAX  FlagValue
	MAX-ACCESS  read-write
	STATUS      current
	DESCRIPTION
	    "Indicates the DEG consequent action of this
	    GSLAM-AG channel."
	::= { gslamAGChannelEntry 30 }

    gslamAGChannelCRSLpbkType     OBJECT-TYPE
    SYNTAX      INTEGER {
        unknown(1),
        not-present(2),
        operate(3),
        release(4)
    }
    MAX-ACCESS  read-write
    STATUS      current
    DESCRIPTION
        "Indicates the cross-connect loopback provisioning for ODU2 or OPVCX channel."
    ::= { gslamAGChannelEntry 31 }

    gslamAGChannelCRSLpbkDuration     OBJECT-TYPE
    SYNTAX  Unsigned32 
    MAX-ACCESS  read-write
    STATUS      current
    DESCRIPTION
        "Indicates the duration of cross-connect loopback."
    ::= { gslamAGChannelEntry 32 }

	gslamAGChannelShapingState		OBJECT-TYPE
		SYNTAX		FlagValue
	    MAX-ACCESS  read-write
		STATUS		current
		DESCRIPTION
			"Indicate the shaping state of channel."
	    ::= { gslamAGChannelEntry 33 }

	gslamAGChannelShapingRate		OBJECT-TYPE
		SYNTAX		INTEGER { not-applicable(0), rate-10m(10000),rate-100m(100000),rate-1000m(1000000) }
	    MAX-ACCESS  read-write
		STATUS		current
		DESCRIPTION
			"Indicate the shaping rate of channel."
	    ::= { gslamAGChannelEntry 34 }

-- ************** ESOM SUPPORT STARTS **************
	
	gslamAGChannelLocalExtn           OBJECT-TYPE
		SYNTAX          INTEGER 
								{
								not-applicable(0),
								zero(1),
								ten(2),
								twenty(3),
								thirty(4),
								forty(5),
								fifty(6),
								sixty(7),
								seventy(8),
								eighty(9),
								ninety(10),
								hundred(11)
								}
		MAX-ACCESS      read-write
		STATUS          current
		DESCRIPTION
			"Indicates the maximum allowed distance b/w CN4200 client port and directly attached equipment"
		::= { gslamAGChannelEntry 35 }

	gslamAGChannelNwExtn           OBJECT-TYPE
		SYNTAX          INTEGER {
					not-applicable(1),
					normal(2),
					maximum(3)
					}
		MAX-ACCESS      read-write
		STATUS          current
		DESCRIPTION
			"Indicates the network distance extension mode"
		::= { gslamAGChannelEntry 36 }

	gslamAGChannelCompression           OBJECT-TYPE
			SYNTAX        	FlagValue  
			MAX-ACCESS      read-write
			STATUS          current
			DESCRIPTION
				"Provision the compression datapath option against the CAG channel"
		::= { gslamAGChannelEntry 37 }

	gslamAGChannelNDP		OBJECT-TYPE
		SYNTAX        	FlagValue 
		MAX-ACCESS      read-write
		STATUS          current
		DESCRIPTION
			"Indicate the state of NDP on the specific network optical interface"
		::= { gslamAGChannelEntry 38 }


	gslamAGChannelOSPF		OBJECT-TYPE
		SYNTAX        	FlagValue 
		MAX-ACCESS      read-write
		STATUS          current
		DESCRIPTION
			"Indicate the state of the OSPF Protocol for the interface port"
		::= { gslamAGChannelEntry 39 }

	gslamAGChannelGroupSize           OBJECT-TYPE
			SYNTAX          INTEGER
					{
					not-applicable(1),
					sts48c(2),
					sts12c(3),
					sts3c(4),
					vc4-16c(5),
					vc4-4c(6),
					vc4(7)
					}
			MAX-ACCESS      read-write
			STATUS          current
			DESCRIPTION
				"Indicates the number of concatenated sts-1/vc4, default is zero"
		::= { gslamAGChannelEntry 40 }
	
	-- ************** ESOM SUPPORT ENDS **************
	
	-- UV 5.0 START

	-- channel objects
	gslamAGREL50ChannelTable		OBJECT-TYPE
		SYNTAX		SEQUENCE OF GslamAGREL50ChannelEntry
		MAX-ACCESS	not-accessible
		STATUS		current
		DESCRIPTION
			"A table about the channel info of GSLAM-AG."
	    ::= { ipiGslamAGChannelObjs 2}

	gslamAGREL50ChannelEntry OBJECT-TYPE
		SYNTAX  		GslamAGREL50ChannelEntry
		MAX-ACCESS	not-accessible
		STATUS  		current
		DESCRIPTION
			"A row in channel table.
			Entries can't be deleted or created via SNMP ops."
		INDEX   { gslamAGREL50ShelfIndex, gslamAGREL50IOModuleIndex, gslamAGREL50PortIndex, gslamAGREL50ChannelIndex }
	    ::= { gslamAGREL50ChannelTable 1 }


	GslamAGREL50ChannelEntry ::= SEQUENCE {
		gslamAGREL50ChannelIndex		Unsigned32,
		gslamAGREL50ChannelType		EquipmentTypeValue,
		gslamAGREL50ChannelAction		ActionValue,
		gslamAGREL50ChannelPrimaryState	PrimaryStateValue,
		gslamAGREL50ChannelSecondaryState	SecondaryStateValue,
		gslamAGREL50ChannelProtFunction	ProtectionEntityValue,
		gslamAGREL50ChannelExpTrc		OCTET STRING,   -- EXPTRC
		gslamAGREL50ChannelTrc		    OCTET STRING,   -- TRC
		gslamAGREL50ChannelReceivedTrc	OCTET STRING,	-- INCTRC
		gslamAGREL50ChannelSFThreshold	Unsigned32,     -- SFTH
		gslamAGREL50ChannelSDThreshold	Unsigned32,     -- SDTH
		gslamAGREL50ChannelSESThreshold	Unsigned32,     -- SESTH
		gslamAGREL50ChannelCSESThreshold Unsigned32, 	-- CSESTH
		gslamAGREL50ChannelDegMonLev 	Unsigned32,     -- DEGM
		gslamAGREL50ChannelDegThreshold  Integer32,	    -- DEGTHR
		gslamAGREL50ChannelOCIProtSwitch FlagValue,	    -- OCIPS
		gslamAGREL50ChannelTIMDetectMode TIMModeValue,   -- TIMDETM
		gslamAGREL50ChannelTIMActDisable FlagValue,	-- TIMACTDIS
		gslamAGREL50ChannelExpSAPI   	OCTET STRING,	-- EXPSAPI
		gslamAGREL50ChannelExpDAPI   	OCTET STRING,   -- EXPDAPI
		gslamAGREL50ChannelExpOperSpecified   OCTET STRING,   -- EXPOPR
		gslamAGREL50ChannelTrcSAPI   	OCTET STRING,	-- TRCSAPI
		gslamAGREL50ChannelTrcDAPI   	OCTET STRING,   -- TRCDAPI
		gslamAGREL50ChannelTrcOperSpecified   OCTET STRING,   -- TRCOPR
		gslamAGREL50ChannelReceivedTrcSAPI   OCTET STRING,
		gslamAGREL50ChannelReceivedTrcDAPI   OCTET STRING,
		gslamAGREL50ChannelReceivedTrcOperSpecified   OCTET STRING,
		gslamAGREL50ChannelMuxStructure	INTEGER,
		gslamAGREL50ChannelDEGAction		FlagValue,
		gslamAGREL50ChannelNomTxPwrOCC	OCTET STRING,
		gslamAGREL50ChannelITUNumber	Unsigned32,
		gslamAGREL50ChannelRxNomOptPwr	OCTET STRING,
		gslamAGREL50ChannelTxNomOptPwr	OCTET STRING,
		gslamAGREL50ChannelOptPwrCtrl INTEGER,
		gslamAGREL50ChannelTxOptPwr OCTET STRING,
		gslamAGREL50ChannelRxOptPwr OCTET STRING,
        gslamAGREL50ChannelPreEmphasisOffset OCTET STRING,
        gslamAGREL50ChannelCRSLpbkType       INTEGER,
        gslamAGREL50ChannelCRSLpbkDuration   Unsigned32,
		gslamAGREL50ChannelShapingState		FlagValue,
		gslamAGREL50ChannelShapingRate		INTEGER,
        gslamAGREL50ChannelLocalExtn	INTEGER,
		gslamAGREL50ChannelNwExtn	INTEGER,
		gslamAGREL50ChannelCompression	FlagValue,
		gslamAGREL50ChannelNDP		FlagValue,
		gslamAGREL50ChannelOSPF		FlagValue,
		gslamAGREL50ChannelGroupSize	INTEGER        
	}

	gslamAGREL50ChannelIndex	OBJECT-TYPE
		SYNTAX		Unsigned32
		MAX-ACCESS	not-accessible
		STATUS		current
		DESCRIPTION
			"Index of GSLAM-AG channel table. It uniquely identifies
			each channel. This value is ITU channel number {16-59}
			for an occ channel in an OTS/OPS port"
    	::= { gslamAGREL50ChannelEntry 1 }

	gslamAGREL50ChannelType	OBJECT-TYPE
		SYNTAX		EquipmentTypeValue
		MAX-ACCESS	read-only
		STATUS		current
		DESCRIPTION
			"Indicate the equipment type of this GSLAM-AG channel."
	    ::= { gslamAGREL50ChannelEntry 2 }

    gslamAGREL50ChannelAction     OBJECT-TYPE
	SYNTAX      ActionValue
	MAX-ACCESS  read-write
	STATUS      current
	DESCRIPTION
	    "Indicate command issued to this GSLAM-AG channel."
	::= { gslamAGREL50ChannelEntry 3 }

	gslamAGREL50ChannelPrimaryState	OBJECT-TYPE
		SYNTAX	PrimaryStateValue
 	 	MAX-ACCESS  read-only
 	 	STATUS      current
 	 	DESCRIPTION
			"Indicates the primary state of this GSLAM-AG channel."
 	 	::= { gslamAGREL50ChannelEntry 4 }

	gslamAGREL50ChannelSecondaryState	OBJECT-TYPE
		SYNTAX	SecondaryStateValue
 	 	MAX-ACCESS  read-only
 	 	STATUS      current
 	 	DESCRIPTION
		    "Indicates the secondary state of this GSLAM-AG channel."
 	 	::= { gslamAGREL50ChannelEntry 5 }

	gslamAGREL50ChannelProtFunction	OBJECT-TYPE
		SYNTAX	ProtectionEntityValue
		MAX-ACCESS  read-only
		STATUS      current
		DESCRIPTION
			"Indicates the protection function of this GSLAM-AG channel."
		::= { gslamAGREL50ChannelEntry 6 }

    gslamAGREL50ChannelExpTrc		OBJECT-TYPE
		SYNTAX		OCTET STRING(SIZE(0..64))
		MAX-ACCESS	read-write
		STATUS		current
		DESCRIPTION
			"Indicates the expected trace value of the GSLAM-AG channel."
		::= { gslamAGREL50ChannelEntry 7 }

	gslamAGREL50ChannelTrc		OBJECT-TYPE
		SYNTAX		OCTET STRING(SIZE(0..64))
		MAX-ACCESS	read-write
		STATUS		current
		DESCRIPTION
			"Indicates the transmitted trace value of the GSLAM-AG
			channel."
		::= { gslamAGREL50ChannelEntry 8 }

	gslamAGREL50ChannelReceivedTrc     OBJECT-TYPE
	SYNTAX      OCTET STRING(SIZE(1..64))
	MAX-ACCESS  read-only
	STATUS      current
	DESCRIPTION
	    "Indicates the received trace value of the GSLAM-AG
	    channel."
	::= { gslamAGREL50ChannelEntry 9 }

    gslamAGREL50ChannelSFThreshold		OBJECT-TYPE
		SYNTAX	Unsigned32
		MAX-ACCESS  read-write
		STATUS      current
		DESCRIPTION
			"Indicates the signal fail threshold value of this
			GSLAM-AG channel."
		::= { gslamAGREL50ChannelEntry 10 }

    gslamAGREL50ChannelSDThreshold		OBJECT-TYPE
		SYNTAX	Unsigned32
		MAX-ACCESS  read-write
		STATUS      current
		DESCRIPTION
		    "Indicates the signal degrade threshold value of this
			GSLAM-AG channel."
		::= { gslamAGREL50ChannelEntry 11 }

	gslamAGREL50ChannelSESThreshold		OBJECT-TYPE
		SYNTAX	Unsigned32
		MAX-ACCESS  read-write
		STATUS      current
		DESCRIPTION
			"Indicates the severely errored seconds declaration
			threshold value of this GSLAM-AG channel."
	    ::= { gslamAGREL50ChannelEntry 12 }

    gslamAGREL50ChannelCSESThreshold     OBJECT-TYPE
	SYNTAX  Unsigned32
	MAX-ACCESS  read-write
	STATUS      current
	DESCRIPTION
	    "Indicates the consecutive signal errored seconds
	    declaration threshold value of this GSLAM-AG channel."
	::= { gslamAGREL50ChannelEntry 13 }

    gslamAGREL50ChannelDegMonLev OBJECT-TYPE
	SYNTAX  Unsigned32
	MAX-ACCESS  read-write
	STATUS      current
	DESCRIPTION
	    "Indicates the degrade monitored level value of this
	    GSLAM-AG channel."
	::= { gslamAGREL50ChannelEntry 14 }

    gslamAGREL50ChannelDegThreshold  OBJECT-TYPE
	SYNTAX  Integer32
	MAX-ACCESS  read-write
	STATUS      current
	DESCRIPTION
	    "Indicates the degrade threshold value (percentage of
	    errored blocks) of this GSLAM-AG channel. -1 mean not applicable"
	::= { gslamAGREL50ChannelEntry 15 }

    gslamAGREL50ChannelOCIProtSwitch OBJECT-TYPE
	SYNTAX  FlagValue
	MAX-ACCESS  read-write
	STATUS      current
	DESCRIPTION
	    "Indicates the OCI consequent action value of this
	    GSLAM-AG channel."
	::= { gslamAGREL50ChannelEntry 16 }

    gslamAGREL50ChannelTIMDetectMode OBJECT-TYPE
	SYNTAX  TIMModeValue
	MAX-ACCESS  read-write
	STATUS      current
	DESCRIPTION
	    "Indicates the TIM detection mode value of this
	    GSLAM-AG channel."
	::= { gslamAGREL50ChannelEntry 17 }

    gslamAGREL50ChannelTIMActDisable OBJECT-TYPE
	SYNTAX  FlagValue
	MAX-ACCESS  read-write
	STATUS      current
	DESCRIPTION
	    "Indicates the TIM consequent action value of this
	    GSLAM-AG channel."
	::= { gslamAGREL50ChannelEntry 18 }

    gslamAGREL50ChannelExpSAPI   OBJECT-TYPE
	SYNTAX      OCTET STRING(SIZE(0..15))
	MAX-ACCESS  read-write
	STATUS      current
	DESCRIPTION
	    "Indicate the expected SAPI value of this GSLAM-AG
	    channel."
	::= { gslamAGREL50ChannelEntry 19 }

    gslamAGREL50ChannelExpDAPI   OBJECT-TYPE
	SYNTAX      OCTET STRING(SIZE(0..15))
	MAX-ACCESS  read-write
	STATUS      current
	DESCRIPTION
	    "Indicate the expected DAPI value of this GSLAM-AG
	    channel."
	::= { gslamAGREL50ChannelEntry 20 }

    gslamAGREL50ChannelExpOperSpecified   OBJECT-TYPE
	SYNTAX      OCTET STRING(SIZE(0..32))
	MAX-ACCESS  read-write
	STATUS      current
	DESCRIPTION
	    "Indicate the expected operator specified value of this
	    GSLAM-AG channel."
	::= { gslamAGREL50ChannelEntry 21 }

    gslamAGREL50ChannelTrcSAPI   OBJECT-TYPE
	SYNTAX      OCTET STRING(SIZE(0..15))
	MAX-ACCESS  read-write
	STATUS      current
	DESCRIPTION
	    "Indicate the transmitted SAPI value of this GSLAM-AG
	    channel."
	::= { gslamAGREL50ChannelEntry 22 }

    gslamAGREL50ChannelTrcDAPI   OBJECT-TYPE
	SYNTAX      OCTET STRING(SIZE(0..15))
	MAX-ACCESS  read-write
	STATUS      current
	DESCRIPTION
	    "Indicate the transmitted DAPI value of this GSLAM-AG
	    channel."
	::= { gslamAGREL50ChannelEntry 23 }

    gslamAGREL50ChannelTrcOperSpecified   OBJECT-TYPE
	SYNTAX      OCTET STRING(SIZE(0..32))
	MAX-ACCESS  read-write
	STATUS      current
	DESCRIPTION
	    "Indicate the transmitted operator specified value of
	    this GSLAM-AG channel."
	::= { gslamAGREL50ChannelEntry 24 }

    gslamAGREL50ChannelReceivedTrcSAPI   OBJECT-TYPE
	SYNTAX      OCTET STRING(SIZE(0..15))
	MAX-ACCESS  read-only
	STATUS      current
	DESCRIPTION
	    "Indicate the received SAPI value of this GSLAM-AG
	    channel."
	::= { gslamAGREL50ChannelEntry 25 }

    gslamAGREL50ChannelReceivedTrcDAPI   OBJECT-TYPE
	SYNTAX      OCTET STRING(SIZE(0..15))
	MAX-ACCESS  read-only
	STATUS      current
	DESCRIPTION
	    "Indicate the received DAPI value of this GSLAM-AG
	    channel."
	::= { gslamAGREL50ChannelEntry 26 }

    gslamAGREL50ChannelReceivedTrcOperSpecified   OBJECT-TYPE
	SYNTAX      OCTET STRING(SIZE(0..32))
	MAX-ACCESS  read-only
	STATUS      current
	DESCRIPTION
	    "Indicate the received operator specified value of
	    this GSLAM-AG channel."
	::= { gslamAGREL50ChannelEntry 27 }

    gslamAGREL50ChannelMuxStructure    OBJECT-TYPE
	SYNTAX      INTEGER {
	    unknown(1),
	    not-present(2),
	    channelized(3),
	    clear(4)
	}
	MAX-ACCESS  read-write
	STATUS      current
	DESCRIPTION
	    "Indicates the multiplex structure for an ODUk channel."
	::= { gslamAGREL50ChannelEntry 28 }

    gslamAGREL50ChannelDEGAction		OBJECT-TYPE
	SYNTAX  FlagValue
	MAX-ACCESS  read-write
	STATUS      current
	DESCRIPTION
	    "Indicates the DEG consequent action of this
	    GSLAM-AG channel."
	::= { gslamAGREL50ChannelEntry 29 }

	gslamAGREL50ChannelNomTxPwrOCC    OBJECT-TYPE
    	SYNTAX  	OCTET STRING(SIZE(0..15))
    	MAX-ACCESS  read-write
	   	STATUS      current
    	DESCRIPTION
        	"The nominal transmit power of the occ channel in OTS/OPS port"
   	::= {gslamAGREL50ChannelEntry 30}

	gslamAGREL50ChannelITUNumber 	OBJECT-TYPE
        SYNTAX      Unsigned32
        MAX-ACCESS  read-write
        STATUS      current
        DESCRIPTION
             "The support wavelngth for the occ channel"
    ::= {gslamAGREL50ChannelEntry 31}

	gslamAGREL50ChannelRxNomOptPwr    OBJECT-TYPE
    	SYNTAX  	OCTET STRING(SIZE(0..15))
    	MAX-ACCESS  read-write
   	 	STATUS      current
    	DESCRIPTION
     		"The nominal rx optical power of the optical channel.
			 The default value would be N/A."
   	::= {gslamAGREL50ChannelEntry 32}

	gslamAGREL50ChannelTxNomOptPwr    OBJECT-TYPE
    	SYNTAX  	OCTET STRING(SIZE(0..15))
    	MAX-ACCESS  read-write
   	 	STATUS      current
    	DESCRIPTION
     		"The nominal tx optical power of the optical channel.
			 The default value would be N/A."
   	::= {gslamAGREL50ChannelEntry 33}

	gslamAGREL50ChannelOptPwrCtrl    OBJECT-TYPE
      	SYNTAX  INTEGER {
         	 unknown(1),
           	 manual(2),
           	 auto(3),
           	 not-applicable(4)
		}
    	MAX-ACCESS  read-write
   		STATUS      current
    	DESCRIPTION
    		 "This is a flag with value MAN|AUTO for OCC channels.
				For non-occ channels this value will be (4)"
   	::= {gslamAGREL50ChannelEntry 34}

	gslamAGREL50ChannelTxOptPwr    OBJECT-TYPE
    	SYNTAX  	OCTET STRING(SIZE(0..15))
    	MAX-ACCESS  read-write
   	 	STATUS      current
    	DESCRIPTION
     		"The actual tx optical power of the optical channel.
			 The default value would be N/A."
   	::= {gslamAGREL50ChannelEntry 35}

	gslamAGREL50ChannelRxOptPwr    OBJECT-TYPE
    	SYNTAX  	OCTET STRING(SIZE(0..15))
    	MAX-ACCESS  read-write
   	 	STATUS      current
    	DESCRIPTION
     		"The actual rx optical power of the optical channel.
			 The default value would be N/A."
   	::= {gslamAGREL50ChannelEntry 36}

    gslamAGREL50ChannelPreEmphasisOffset    OBJECT-TYPE
        SYNTAX      OCTET STRING(SIZE(0..15))
        MAX-ACCESS  read-only
        STATUS      current
        DESCRIPTION
            "The pre-emphasis offset of the optical channel."
    ::= {gslamAGREL50ChannelEntry 37}

    gslamAGREL50ChannelCRSLpbkType     OBJECT-TYPE
    SYNTAX      INTEGER {
        unknown(1),
        not-present(2),
        operate(3),
        release(4)
    }
    MAX-ACCESS  read-write
    STATUS      current
    DESCRIPTION
        "Indicates the cross-connect loopback provisioning for ODU2 or OPVCX channel."
    ::= { gslamAGREL50ChannelEntry 38 }

    gslamAGREL50ChannelCRSLpbkDuration     OBJECT-TYPE
    SYNTAX  Unsigned32
    MAX-ACCESS  read-write
    STATUS      current
    DESCRIPTION
        "Indicates the duration of cross-connect loopback."
    ::= { gslamAGREL50ChannelEntry 39 }

	gslamAGREL50ChannelShapingState		OBJECT-TYPE
		SYNTAX		FlagValue
	    MAX-ACCESS  read-write
		STATUS		current
		DESCRIPTION
			"Indicate the shaping state of channel."
	    ::= { gslamAGREL50ChannelEntry 40 }

	gslamAGREL50ChannelShapingRate		OBJECT-TYPE
		SYNTAX		INTEGER { rate-10m(10000),rate-100m(100000),rate-1000m(1000000) }
	    MAX-ACCESS  read-write
		STATUS		current
		DESCRIPTION
			"Indicate the shaping rate of channel."
	    ::= { gslamAGREL50ChannelEntry 41 }


	-- ************** ESOM SUPPORT STARTS **************
		gslamAGREL50ChannelLocalExtn           OBJECT-TYPE
			SYNTAX          INTEGER 
									{
									not-applicable(0),
									zero(1),
									ten(2),
									twenty(3),
									thirty(4),
									forty(5),
									fifty(6),
									sixty(7),
									seventy(8),
									eighty(9),
									ninety(10),
									hundred(11)
									}	
			MAX-ACCESS      read-write
			STATUS          current
			DESCRIPTION
				"Indicates the maximum allowed distance b/w CN4200 client port and directly attached equipment"
			::= { gslamAGREL50ChannelEntry 42 }
	
		gslamAGREL50ChannelNwExtn           OBJECT-TYPE
			SYNTAX          INTEGER {
						not-applicable(1),
						normal(2),
						maximum(3)
						}
			MAX-ACCESS      read-write
			STATUS          current
			DESCRIPTION
				"Indicates the network distance extension mode"
			::= { gslamAGREL50ChannelEntry 43 }
	
		gslamAGREL50ChannelCompression           OBJECT-TYPE
				SYNTAX        	FlagValue  
				MAX-ACCESS      read-write
				STATUS          current
				DESCRIPTION
					"Provision the compression datapath option against the CAG channel"
			::= { gslamAGREL50ChannelEntry 44 }
	
		gslamAGREL50ChannelNDP		OBJECT-TYPE
			SYNTAX        	FlagValue 
			MAX-ACCESS      read-write
			STATUS          current
			DESCRIPTION
				"Indicate the state of NDP on the specific network optical interface"
			::= { gslamAGREL50ChannelEntry 45 }
	
	
		gslamAGREL50ChannelOSPF		OBJECT-TYPE
			SYNTAX        	FlagValue 
			MAX-ACCESS      read-write
			STATUS          current
			DESCRIPTION
				"Indicate the state of the OSPF Protocol for the interface port"
			::= { gslamAGREL50ChannelEntry 46 }
	
		gslamAGREL50ChannelGroupSize           OBJECT-TYPE
				SYNTAX          INTEGER
						{
						not-applicable(1),
						sts48c(2),
						sts12c(3),
						sts3c(5),
						vc4-16c(6),
						vc4-4c(7),
						vc4(8)
						}
				MAX-ACCESS      read-write
				STATUS          current
				DESCRIPTION
					"Indicates the number of concatenated sts-1/vc4, default is zero"
			::= { gslamAGREL50ChannelEntry 47 }
	
	-- ************** ESOM SUPPORT ENDS **************
	-- UV 5.0 END

	-- OCC channel objects
	gslamAGOCCChannelTable		OBJECT-TYPE
		SYNTAX		SEQUENCE OF GslamAGOCCChannelEntry
		MAX-ACCESS	not-accessible
		STATUS		current
		DESCRIPTION
			"A table about the channel info of GSLAM-AG."
	    ::= { ipiGslamAGChannelObjs 3}

	gslamAGOCCChannelEntry OBJECT-TYPE
		SYNTAX  		GslamAGOCCChannelEntry
		MAX-ACCESS	not-accessible
		STATUS  		current
		DESCRIPTION
			"A row in channel table.
			Entries can't be deleted or created via SNMP ops."
		INDEX   { gslamAGShelfIndex, gslamAGIOModuleIndex, gslamAGPortIndex, gslamAGChannelIndex }
	    ::= { gslamAGOCCChannelTable 1 }


	GslamAGOCCChannelEntry ::= SEQUENCE {
		gslamAGOCCChannelIndex		Unsigned32,
		gslamAGOCCChannelType		EquipmentTypeValue,
		gslamAGOCCChannelAction		ActionValue,
		gslamAGOCCChannelPrimaryState	PrimaryStateValue,
		gslamAGOCCChannelSecondaryState	SecondaryStateValue,
		gslamAGOCCChannelProtFunction	ProtectionEntityValue,
		gslamAGOCCChannelExpTrc		OCTET STRING,   -- EXPTRC
		gslamAGOCCChannelTrc		    OCTET STRING,   -- TRC
		gslamAGOCCChannelReceivedTrc	OCTET STRING,	-- INCTRC
		gslamAGOCCChannelSFThreshold	Unsigned32,     -- SFTH
		gslamAGOCCChannelSDThreshold	Unsigned32,     -- SDTH
		gslamAGOCCChannelSESThreshold	Unsigned32,     -- SESTH
		gslamAGOCCChannelCSESThreshold Unsigned32, 	-- CSESTH
		gslamAGOCCChannelDegMonLev 	Unsigned32,     -- DEGM
		gslamAGOCCChannelDegThreshold  Integer32,	    -- DEGTHR
		gslamAGOCCChannelOCIProtSwitch FlagValue,	    -- OCIPS
		gslamAGOCCChannelTIMDetectMode TIMModeValue,   -- TIMDETM
		gslamAGOCCChannelTIMActDisable FlagValue,	-- TIMACTDIS
		gslamAGOCCChannelExpSAPI   	OCTET STRING,	-- EXPSAPI
		gslamAGOCCChannelExpDAPI   	OCTET STRING,   -- EXPDAPI
		gslamAGOCCChannelExpOperSpecified   OCTET STRING,   -- EXPOPR
		gslamAGOCCChannelTrcSAPI   	OCTET STRING,	-- TRCSAPI
		gslamAGOCCChannelTrcDAPI   	OCTET STRING,   -- TRCDAPI
		gslamAGOCCChannelTrcOperSpecified   OCTET STRING,   -- TRCOPR
		gslamAGOCCChannelReceivedTrcSAPI   OCTET STRING,
		gslamAGOCCChannelReceivedTrcDAPI   OCTET STRING,
		gslamAGOCCChannelReceivedTrcOperSpecified   OCTET STRING,
		gslamAGOCCChannelMuxStructure	INTEGER,
		gslamAGOCCChannelDEGAction		FlagValue,
		gslamAGOCCChannelNomTxPwrOCC	OCTET STRING,
		gslamAGOCCChannelITUNumber	Unsigned32,
		gslamAGOCCChannelRxNomOptPwr	OCTET STRING,
		gslamAGOCCChannelTxNomOptPwr	OCTET STRING,
		gslamAGOCCChannelOptPwrCtrl INTEGER,
		gslamAGOCCChannelTxOptPwr	OCTET STRING,
		gslamAGOCCChannelRxOptPwr	OCTET STRING,
        gslamAGOCCChannelPreEmphasisOffset    OCTET STRING
	}

	gslamAGOCCChannelIndex	OBJECT-TYPE
		SYNTAX		Unsigned32
		MAX-ACCESS	not-accessible
		STATUS		current
		DESCRIPTION
			"Index of GSLAM-AG channel table. It uniquely identifies
			each channel. This value is ITU channel number {16-59}
			for an occ channel in an OTS/OPS port"
    	::= { gslamAGOCCChannelEntry 1 }

	gslamAGOCCChannelType	OBJECT-TYPE
		SYNTAX		EquipmentTypeValue
		MAX-ACCESS	read-only
		STATUS		current
		DESCRIPTION
			"Indicate the equipment type of this GSLAM-AG channel."
	    ::= { gslamAGOCCChannelEntry 2 }

    gslamAGOCCChannelAction     OBJECT-TYPE
	SYNTAX      ActionValue
	MAX-ACCESS  read-write
	STATUS      current
	DESCRIPTION
	    "Indicate command issued to this GSLAM-AG channel."
	::= { gslamAGOCCChannelEntry 3 }

	gslamAGOCCChannelPrimaryState	OBJECT-TYPE
		SYNTAX	PrimaryStateValue
 	 	MAX-ACCESS  read-only
 	 	STATUS      current
 	 	DESCRIPTION
			"Indicates the primary state of this GSLAM-AG channel."
 	 	::= { gslamAGOCCChannelEntry 4 }

	gslamAGOCCChannelSecondaryState	OBJECT-TYPE
		SYNTAX	SecondaryStateValue
 	 	MAX-ACCESS  read-only
 	 	STATUS      current
 	 	DESCRIPTION
		    "Indicates the secondary state of this GSLAM-AG channel."
 	 	::= { gslamAGOCCChannelEntry 5 }

	gslamAGOCCChannelProtFunction	OBJECT-TYPE
		SYNTAX	ProtectionEntityValue
		MAX-ACCESS  read-only
		STATUS      current
		DESCRIPTION
			"Indicates the protection function of this GSLAM-AG channel."
		::= { gslamAGOCCChannelEntry 6 }

    gslamAGOCCChannelExpTrc		OBJECT-TYPE
		SYNTAX		OCTET STRING(SIZE(0..64))
		MAX-ACCESS	read-write
		STATUS		current
		DESCRIPTION
			"Indicates the expected trace value of the GSLAM-AG channel."
		::= { gslamAGOCCChannelEntry 7 }

	gslamAGOCCChannelTrc		OBJECT-TYPE
		SYNTAX		OCTET STRING(SIZE(0..64))
		MAX-ACCESS	read-write
		STATUS		current
		DESCRIPTION
			"Indicates the transmitted trace value of the GSLAM-AG
			channel."
		::= { gslamAGOCCChannelEntry 8 }

	gslamAGOCCChannelReceivedTrc     OBJECT-TYPE
	SYNTAX      OCTET STRING(SIZE(1..64))
	MAX-ACCESS  read-only
	STATUS      current
	DESCRIPTION
	    "Indicates the received trace value of the GSLAM-AG
	    channel."
	::= { gslamAGOCCChannelEntry 9 }

    gslamAGOCCChannelSFThreshold		OBJECT-TYPE
		SYNTAX	Unsigned32
		MAX-ACCESS  read-write
		STATUS      current
		DESCRIPTION
			"Indicates the signal fail threshold value of this
			GSLAM-AG channel."
		::= { gslamAGOCCChannelEntry 10 }

    gslamAGOCCChannelSDThreshold		OBJECT-TYPE
		SYNTAX	Unsigned32
		MAX-ACCESS  read-write
		STATUS      current
		DESCRIPTION
		    "Indicates the signal degrade threshold value of this
			GSLAM-AG channel."
		::= { gslamAGOCCChannelEntry 11 }

	gslamAGOCCChannelSESThreshold		OBJECT-TYPE
		SYNTAX	Unsigned32
		MAX-ACCESS  read-write
		STATUS      current
		DESCRIPTION
			"Indicates the seveOCCy errored seconds declaration
			threshold value of this GSLAM-AG channel."
	    ::= { gslamAGOCCChannelEntry 12 }

    gslamAGOCCChannelCSESThreshold     OBJECT-TYPE
	SYNTAX  Unsigned32
	MAX-ACCESS  read-write
	STATUS      current
	DESCRIPTION
	    "Indicates the consecutive signal errored seconds
	    declaration threshold value of this GSLAM-AG channel."
	::= { gslamAGOCCChannelEntry 13 }

    gslamAGOCCChannelDegMonLev OBJECT-TYPE
	SYNTAX  Unsigned32
	MAX-ACCESS  read-write
	STATUS      current
	DESCRIPTION
	    "Indicates the degrade monitored level value of this
	    GSLAM-AG channel."
	::= { gslamAGOCCChannelEntry 14 }

    gslamAGOCCChannelDegThreshold  OBJECT-TYPE
	SYNTAX  Integer32
	MAX-ACCESS  read-write
	STATUS      current
	DESCRIPTION
	    "Indicates the degrade threshold value (percentage of
	    errored blocks) of this GSLAM-AG channel. -1 mean not applicable"
	::= { gslamAGOCCChannelEntry 15 }

    gslamAGOCCChannelOCIProtSwitch OBJECT-TYPE
	SYNTAX  FlagValue
	MAX-ACCESS  read-write
	STATUS      current
	DESCRIPTION
	    "Indicates the OCI consequent action value of this
	    GSLAM-AG channel."
	::= { gslamAGOCCChannelEntry 16 }

    gslamAGOCCChannelTIMDetectMode OBJECT-TYPE
	SYNTAX  TIMModeValue
	MAX-ACCESS  read-write
	STATUS      current
	DESCRIPTION
	    "Indicates the TIM detection mode value of this
	    GSLAM-AG channel."
	::= { gslamAGOCCChannelEntry 17 }

    gslamAGOCCChannelTIMActDisable OBJECT-TYPE
	SYNTAX  FlagValue
	MAX-ACCESS  read-write
	STATUS      current
	DESCRIPTION
	    "Indicates the TIM consequent action value of this
	    GSLAM-AG channel."
	::= { gslamAGOCCChannelEntry 18 }

    gslamAGOCCChannelExpSAPI   OBJECT-TYPE
	SYNTAX      OCTET STRING(SIZE(0..15))
	MAX-ACCESS  read-write
	STATUS      current
	DESCRIPTION
	    "Indicate the expected SAPI value of this GSLAM-AG
	    channel."
	::= { gslamAGOCCChannelEntry 19 }

    gslamAGOCCChannelExpDAPI   OBJECT-TYPE
	SYNTAX      OCTET STRING(SIZE(0..15))
	MAX-ACCESS  read-write
	STATUS      current
	DESCRIPTION
	    "Indicate the expected DAPI value of this GSLAM-AG
	    channel."
	::= { gslamAGOCCChannelEntry 20 }

    gslamAGOCCChannelExpOperSpecified   OBJECT-TYPE
	SYNTAX      OCTET STRING(SIZE(0..32))
	MAX-ACCESS  read-write
	STATUS      current
	DESCRIPTION
	    "Indicate the expected operator specified value of this
	    GSLAM-AG channel."
	::= { gslamAGOCCChannelEntry 21 }

    gslamAGOCCChannelTrcSAPI   OBJECT-TYPE
	SYNTAX      OCTET STRING(SIZE(0..15))
	MAX-ACCESS  read-write
	STATUS      current
	DESCRIPTION
	    "Indicate the transmitted SAPI value of this GSLAM-AG
	    channel."
	::= { gslamAGOCCChannelEntry 22 }

    gslamAGOCCChannelTrcDAPI   OBJECT-TYPE
	SYNTAX      OCTET STRING(SIZE(0..15))
	MAX-ACCESS  read-write
	STATUS      current
	DESCRIPTION
	    "Indicate the transmitted DAPI value of this GSLAM-AG
	    channel."
	::= { gslamAGOCCChannelEntry 23 }

    gslamAGOCCChannelTrcOperSpecified   OBJECT-TYPE
	SYNTAX      OCTET STRING(SIZE(0..32))
	MAX-ACCESS  read-write
	STATUS      current
	DESCRIPTION
	    "Indicate the transmitted operator specified value of
	    this GSLAM-AG channel."
	::= { gslamAGOCCChannelEntry 24 }

    gslamAGOCCChannelReceivedTrcSAPI   OBJECT-TYPE
	SYNTAX      OCTET STRING(SIZE(0..15))
	MAX-ACCESS  read-only
	STATUS      current
	DESCRIPTION
	    "Indicate the received SAPI value of this GSLAM-AG
	    channel."
	::= { gslamAGOCCChannelEntry 25 }

    gslamAGOCCChannelReceivedTrcDAPI   OBJECT-TYPE
	SYNTAX      OCTET STRING(SIZE(0..15))
	MAX-ACCESS  read-only
	STATUS      current
	DESCRIPTION
	    "Indicate the received DAPI value of this GSLAM-AG
	    channel."
	::= { gslamAGOCCChannelEntry 26 }

    gslamAGOCCChannelReceivedTrcOperSpecified   OBJECT-TYPE
	SYNTAX      OCTET STRING(SIZE(0..32))
	MAX-ACCESS  read-only
	STATUS      current
	DESCRIPTION
	    "Indicate the received operator specified value of
	    this GSLAM-AG channel."
	::= { gslamAGOCCChannelEntry 27 }

    gslamAGOCCChannelMuxStructure    OBJECT-TYPE
	SYNTAX      INTEGER {
	    unknown(1),
	    not-present(2),
	    channelized(3),
	    clear(4)
	}
	MAX-ACCESS  read-write
	STATUS      current
	DESCRIPTION
	    "Indicates the multiplex structure for an ODUk channel."
	::= { gslamAGOCCChannelEntry 28 }

    gslamAGOCCChannelDEGAction		OBJECT-TYPE
	SYNTAX  FlagValue
	MAX-ACCESS  read-write
	STATUS      current
	DESCRIPTION
	    "Indicates the DEG consequent action of this
	    GSLAM-AG channel."
	::= { gslamAGOCCChannelEntry 29 }

	gslamAGOCCChannelNomTxPwrOCC    OBJECT-TYPE
    	SYNTAX  	OCTET STRING(SIZE(0..15))
    	MAX-ACCESS  read-write
	   	STATUS      current
    	DESCRIPTION
        	"The nominal transmit power of the occ channel in OTS/OPS port"
   	::= {gslamAGOCCChannelEntry 30}

	gslamAGOCCChannelITUNumber 	OBJECT-TYPE
        SYNTAX      Unsigned32
        MAX-ACCESS  read-write
        STATUS      current
        DESCRIPTION
             "The support wavelngth for the occ channel"
    ::= {gslamAGOCCChannelEntry 31}

	gslamAGOCCChannelRxNomOptPwr    OBJECT-TYPE
    	SYNTAX  	OCTET STRING(SIZE(0..15))
    	MAX-ACCESS  read-write
   	 	STATUS      current
    	DESCRIPTION
     		"The nominal rx optical power of the optical channel.
			 The default value would be N/A."
   	::= {gslamAGOCCChannelEntry 32}

	gslamAGOCCChannelTxNomOptPwr    OBJECT-TYPE
    	SYNTAX  	OCTET STRING(SIZE(0..15))
    	MAX-ACCESS  read-write
   	 	STATUS      current
    	DESCRIPTION
     		"The nominal tx optical power of the optical channel.
			 The default value would be N/A."
   	::= {gslamAGOCCChannelEntry 33}

	gslamAGOCCChannelOptPwrCtrl    OBJECT-TYPE
      	SYNTAX  INTEGER {
         	 unknown(1),
           	 manual(2),
           	 auto(3),
           	 not-applicable(4)
		}
    	MAX-ACCESS  read-write
   		STATUS      current
    	DESCRIPTION
    		 "This is a flag with value MAN|AUTO for OCC channels.
				For non-occ channels this value will be (4)"
   	::= {gslamAGOCCChannelEntry 34}

	gslamAGOCCChannelTxOptPwr    OBJECT-TYPE
    	SYNTAX  	OCTET STRING(SIZE(0..15))
    	MAX-ACCESS  read-write
   	 	STATUS      current
    	DESCRIPTION
     		"The actual tx optical power of the optical channel.
			 The default value would be N/A."
   	::= {gslamAGOCCChannelEntry 35}

	gslamAGOCCChannelRxOptPwr    OBJECT-TYPE
    	SYNTAX  	OCTET STRING(SIZE(0..15))
    	MAX-ACCESS  read-write
   	 	STATUS      current
    	DESCRIPTION
     		"The actual rx optical power of the optical channel.
			 The default value would be N/A."
   	::= {gslamAGOCCChannelEntry 36}

    gslamAGOCCChannelPreEmphasisOffset    OBJECT-TYPE
        SYNTAX      OCTET STRING(SIZE(0..15))
        MAX-ACCESS  read-only
        STATUS      current
        DESCRIPTION
            "The pre-emphasis offset of the optical channel."
    ::= {gslamAGOCCChannelEntry 37}

	-- concatenated OPVCx objects
	gslamAGConcOPVCxTable		OBJECT-TYPE
		SYNTAX		SEQUENCE OF GslamAGConcOPVCxEntry
		MAX-ACCESS	not-accessible
		STATUS		current
		DESCRIPTION
			"A table about the concatenated OPVCx info of GSLAM-AG."
	    ::= { ipiGslamAGConcOPVCxObjs 1 }

	gslamAGConcOPVCxEntry OBJECT-TYPE
		SYNTAX  		GslamAGConcOPVCxEntry
		MAX-ACCESS	not-accessible
		STATUS  		current
		DESCRIPTION
			"A row in concatenated OPVCx table."
		INDEX   { gslamAGConcOPVCxIndex }
	    ::= { gslamAGConcOPVCxTable 1 }


	GslamAGConcOPVCxEntry ::= SEQUENCE {
		gslamAGConcOPVCxIndex		Unsigned32,
		gslamAGConcOPVCxIfIndex	Unsigned32,
		gslamAGConcOPVCxType		EquipmentTypeValue,
		gslamAGConcOPVCxAction		ActionValue,
		gslamAGConcOPVCxPrimaryState	PrimaryStateValue,
		gslamAGConcOPVCxSecondaryState	SecondaryStateValue,
		gslamAGConcOPVCxProtFunction	ProtectionEntityValue,
		gslamAGConcOPVCxSESThreshold	Unsigned32,     -- SESTH
		gslamAGConcOPVCxCSESThreshold Unsigned32, 	-- CSESTH
		gslamAGConcOPVCxDegMonLev 	Unsigned32,     -- DEGM
		gslamAGConcOPVCxDegThreshold  Integer32,	-- DEGTHR
		gslamAGConcOPVCxOCIProtSwitch FlagValue,	    -- OCIPS
		gslamAGConcOPVCxTIMDetectMode TIMModeValue,   -- TIMDETM
		gslamAGConcOPVCxTIMActDisable FlagValue,	-- TIMACTDIS
		gslamAGConcOPVCxExpSAPI   	OCTET STRING,	-- EXPSAPI
		gslamAGConcOPVCxExpDAPI   	OCTET STRING,   -- EXPDAPI
		gslamAGConcOPVCxExpOperSpecified   OCTET STRING,   -- EXPOPR
		gslamAGConcOPVCxTrcSAPI   	OCTET STRING,	-- TRCSAPI
		gslamAGConcOPVCxTrcDAPI   	OCTET STRING,   -- TRCDAPI
		gslamAGConcOPVCxTrcOperSpecified   OCTET STRING,   -- TRCOPR
		gslamAGConcOPVCxReceivedTrcSAPI   OCTET STRING,
		gslamAGConcOPVCxReceivedTrcDAPI   OCTET STRING,
		gslamAGConcOPVCxReceivedTrcOperSpecified   OCTET STRING,
		gslamAGConcOPVCxExpTrc		OCTET STRING,   -- EXPTRC
		gslamAGConcOPVCxTrc		    OCTET STRING,   -- TRC
		gslamAGConcOPVCxReceivedTrc	OCTET STRING,	-- INCTRC
        gslamAGConcOPVCxCRSLpbkType       INTEGER,
        gslamAGConcOPVCxCRSLpbkDuration   Unsigned32 

		-- gslamAGConcOPVCxRowStatus	RowStatusValue
		-- gslamAGConcOPVCMasterTimeSlot Unsigned32
	}

	gslamAGConcOPVCxIndex	OBJECT-TYPE
		SYNTAX		Unsigned32
		MAX-ACCESS	not-accessible
		STATUS		current
		DESCRIPTION
			"Index of GSLAM-AG concatenated OPVCx table. It uniquely identifies
			each concatenated OPVCx."
    	::= { gslamAGConcOPVCxEntry 1 }

	gslamAGConcOPVCxIfIndex	OBJECT-TYPE
		SYNTAX		Unsigned32
		MAX-ACCESS	read-only
		STATUS		current
		DESCRIPTION
			"Indicate the ifIndex of Mib2's interface table of this
			GSLAM-AG concatenated OPVCx."
	    ::= { gslamAGConcOPVCxEntry 2 }

	gslamAGConcOPVCxType	OBJECT-TYPE
		SYNTAX		EquipmentTypeValue
		MAX-ACCESS	read-only
		STATUS		current
		DESCRIPTION
			"Indicate the equipment type of this GSLAM-AG concatenated OPVCx."
	    ::= { gslamAGConcOPVCxEntry 3 }

    gslamAGConcOPVCxAction     OBJECT-TYPE
	SYNTAX      ActionValue
	MAX-ACCESS  read-write
	STATUS      current
	DESCRIPTION
	    "Indicate command issued to this GSLAM-AG concatenated OPVCx."
	::= { gslamAGConcOPVCxEntry 4 }

	gslamAGConcOPVCxPrimaryState	OBJECT-TYPE
		SYNTAX	PrimaryStateValue
 	 	MAX-ACCESS  read-write
 	 	STATUS      current
 	 	DESCRIPTION
			"Indicates the primary state of this GSLAM-AG concatenated OPVCx."
 	 	::= { gslamAGConcOPVCxEntry 5 }

	gslamAGConcOPVCxSecondaryState	OBJECT-TYPE
		SYNTAX	SecondaryStateValue
 	 	MAX-ACCESS  read-only
 	 	STATUS      current
 	 	DESCRIPTION
		    "Indicates the secondary state of this GSLAM-AG concatenated
		    OPVCx."
 	 	::= { gslamAGConcOPVCxEntry 6 }

	gslamAGConcOPVCxProtFunction	OBJECT-TYPE
		SYNTAX	ProtectionEntityValue
		MAX-ACCESS  read-only
		STATUS      current
		DESCRIPTION
			"Indicates the protection function of this GSLAM-AG concatenated
			OPVCx."
		::= { gslamAGConcOPVCxEntry 7 }

	gslamAGConcOPVCxSESThreshold		OBJECT-TYPE
		SYNTAX	Unsigned32
		MAX-ACCESS  read-write
		STATUS      current
		DESCRIPTION
			"Indicates the severely errored seconds declaration
			threshold value of this GSLAM-AG concatenated OPVCx."
	    ::= { gslamAGConcOPVCxEntry 8 }

    gslamAGConcOPVCxCSESThreshold     OBJECT-TYPE
	SYNTAX  Unsigned32
	MAX-ACCESS  read-write
	STATUS      current
	DESCRIPTION
	    "Indicates the consecutive signal errored seconds
	    declaration threshold value of this GSLAM-AG concatenated OPVCx."
	::= { gslamAGConcOPVCxEntry 9 }

    gslamAGConcOPVCxDegMonLev OBJECT-TYPE
	SYNTAX  Unsigned32
	MAX-ACCESS  read-write
	STATUS      current
	DESCRIPTION
	    "Indicates the degrade monitored level value of this
	    GSLAM-AG concatenated OPVCx."
	::= { gslamAGConcOPVCxEntry 10 }

    gslamAGConcOPVCxDegThreshold  OBJECT-TYPE
	SYNTAX  Integer32
	MAX-ACCESS  read-write
	STATUS      current
	DESCRIPTION
	    "Indicates the degrade threshold value (percentage of
	    errored blocks) of this GSLAM-AG concatenated OPVCx. -1 mean not applicable"
	::= { gslamAGConcOPVCxEntry 11 }

    gslamAGConcOPVCxOCIProtSwitch OBJECT-TYPE
	SYNTAX  FlagValue
	MAX-ACCESS  read-write
	STATUS      current
	DESCRIPTION
	    "Indicates the OCI consequent action value of this
	    GSLAM-AG channel."
	::= { gslamAGConcOPVCxEntry 12 }

    gslamAGConcOPVCxTIMDetectMode OBJECT-TYPE
	SYNTAX  TIMModeValue
	MAX-ACCESS  read-write
	STATUS      current
	DESCRIPTION
	    "Indicates the TIM detection mode value of this
	    GSLAM-AG concatenated OPVCx."
	::= { gslamAGConcOPVCxEntry 13 }

    gslamAGConcOPVCxTIMActDisable OBJECT-TYPE
	SYNTAX  FlagValue
	MAX-ACCESS  read-write
	STATUS      current
	DESCRIPTION
	    "Indicates the TIM consequent action value of this
	    GSLAM-AG concatenated OPVCx."
	::= { gslamAGConcOPVCxEntry 14 }

    gslamAGConcOPVCxExpSAPI   OBJECT-TYPE
	SYNTAX      OCTET STRING(SIZE(0..15))
	MAX-ACCESS  read-write
	STATUS      current
	DESCRIPTION
	    "Indicate the expected SAPI value of this GSLAM-AG
	    concatenated OPVCx."
	::= { gslamAGConcOPVCxEntry 15 }

    gslamAGConcOPVCxExpDAPI   OBJECT-TYPE
	SYNTAX      OCTET STRING(SIZE(0..15))
	MAX-ACCESS  read-write
	STATUS      current
	DESCRIPTION
	    "Indicate the expected DAPI value of this GSLAM-AG
	    concatenated OPVCx."
	::= { gslamAGConcOPVCxEntry 16 }

    gslamAGConcOPVCxExpOperSpecified   OBJECT-TYPE
	SYNTAX      OCTET STRING(SIZE(0..32))
	MAX-ACCESS  read-write
	STATUS      current
	DESCRIPTION
	    "Indicate the expected operator specified value of this
	    GSLAM-AG concatenated OPVCx."
	::= { gslamAGConcOPVCxEntry 17 }

    gslamAGConcOPVCxTrcSAPI   OBJECT-TYPE
	SYNTAX      OCTET STRING(SIZE(0..15))
	MAX-ACCESS  read-write
	STATUS      current
	DESCRIPTION
	    "Indicate the transmitted SAPI value of this GSLAM-AG
	    concatenated OPVCx."
	::= { gslamAGConcOPVCxEntry 18 }

    gslamAGConcOPVCxTrcDAPI   OBJECT-TYPE
	SYNTAX      OCTET STRING(SIZE(0..15))
	MAX-ACCESS  read-write
	STATUS      current
	DESCRIPTION
	    "Indicate the transmitted DAPI value of this GSLAM-AG
	    concatenated OPVCx."
	::= { gslamAGConcOPVCxEntry 19 }

    gslamAGConcOPVCxTrcOperSpecified   OBJECT-TYPE
	SYNTAX      OCTET STRING(SIZE(0..32))
	MAX-ACCESS  read-write
	STATUS      current
	DESCRIPTION
	    "Indicate the transmitted operator specified value of
	    this GSLAM-AG concatenated OPVCx."
	::= { gslamAGConcOPVCxEntry 20 }

    gslamAGConcOPVCxReceivedTrcSAPI   OBJECT-TYPE
	SYNTAX      OCTET STRING(SIZE(0..15))
	MAX-ACCESS  read-only
	STATUS      current
	DESCRIPTION
	    "Indicate the received SAPI value of this GSLAM-AG
	    concatenated OPVCx."
	::= { gslamAGConcOPVCxEntry 21 }

    gslamAGConcOPVCxReceivedTrcDAPI   OBJECT-TYPE
	SYNTAX      OCTET STRING(SIZE(0..15))
	MAX-ACCESS  read-only
	STATUS      current
	DESCRIPTION
	    "Indicate the received DAPI value of this GSLAM-AG
	    concatenated OPVCx."
	::= { gslamAGConcOPVCxEntry 22 }

    gslamAGConcOPVCxReceivedTrcOperSpecified   OBJECT-TYPE
	SYNTAX      OCTET STRING(SIZE(0..32))
	MAX-ACCESS  read-only
	STATUS      current
	DESCRIPTION
	    "Indicate the received operator specified value of
	    this GSLAM-AG concatenated OPVCx."
	::= { gslamAGConcOPVCxEntry 23 }

	gslamAGConcOPVCxExpTrc		OBJECT-TYPE
		SYNTAX		OCTET STRING(SIZE(0..64))
		MAX-ACCESS	read-write
		STATUS		current
		DESCRIPTION
			"Indicates the expected trace value of the GSLAM-AG OPVCx channel."
		::= { gslamAGConcOPVCxEntry 24 }

	gslamAGConcOPVCxTrc		OBJECT-TYPE
		SYNTAX		OCTET STRING(SIZE(0..64))
		MAX-ACCESS	read-write
		STATUS		current
		DESCRIPTION
			"Indicates the transmitted trace value of the GSLAM-AG
			OPVCx."
		::= { gslamAGConcOPVCxEntry 25 }

	gslamAGConcOPVCxReceivedTrc     OBJECT-TYPE
		SYNTAX      OCTET STRING(SIZE(1..64))
		MAX-ACCESS  read-only
		STATUS      current
		DESCRIPTION
	    		"Indicates the received trace value of the GSLAM-AG
	    		OPVCx."
	::= { gslamAGConcOPVCxEntry 26 }

    gslamAGConcOPVCxCRSLpbkType     OBJECT-TYPE
    SYNTAX      INTEGER {
        unknown(1),
        not-present(2),
        operate(3),
        release(4)
    }
    MAX-ACCESS  read-write
    STATUS      current
    DESCRIPTION
        "Indicates the cross-connect loopback provisioning for OPVCX channel."
    ::= { gslamAGConcOPVCxEntry 27 }

    gslamAGConcOPVCxCRSLpbkDuration     OBJECT-TYPE
    SYNTAX  Unsigned32
    MAX-ACCESS  read-write
    STATUS      current
    DESCRIPTION
        "Indicates the duration of cross-connect loopback."
    ::= { gslamAGConcOPVCxEntry 28 }


	-- UV 5.0 CHANGE START 
	-- concatenated OPVCx objects
    gslamAGREL50ConcOPVCxTable           OBJECT-TYPE
         SYNTAX          SEQUENCE OF GslamAGREL50ConcOPVCxEntry
         MAX-ACCESS      not-accessible
         STATUS          current
         DESCRIPTION
                "A table about the concatenated OPVCx info of GSLAM-AG."
    ::= { ipiGslamAGConcOPVCxObjs 2 }

    gslamAGREL50ConcOPVCxEntry OBJECT-TYPE
         SYNTAX                  GslamAGREL50ConcOPVCxEntry
         MAX-ACCESS      not-accessible
         STATUS                  current
         DESCRIPTION
             "A row in concatenated OPVCx table."
         INDEX   { gslamAGREL50ConcOPVCxSIndex, gslamAGREL50ConcOPVCxMIndex,
                   gslamAGREL50ConcOPVCxPIndex, gslamAGREL50ConcOPVCxCIndex,
                   gslamAGREL50ConcOPVCxTIndex }
     ::= { gslamAGREL50ConcOPVCxTable 1 }

	 GslamAGREL50ConcOPVCxEntry ::= SEQUENCE {
		    gslamAGREL50ConcOPVCxSIndex          			Unsigned32,
            gslamAGREL50ConcOPVCxMIndex          			Unsigned32,
            gslamAGREL50ConcOPVCxPIndex          			Unsigned32,
            gslamAGREL50ConcOPVCxCIndex          			Unsigned32,
            gslamAGREL50ConcOPVCxTIndex          			Unsigned32,
            --gslamAGREL50ConcOPVCxIfIndex       			Unsigned32,
            gslamAGREL50ConcOPVCxType            			EquipmentTypeValue,
            gslamAGREL50ConcOPVCxAction          			ActionValue,
            gslamAGREL50ConcOPVCxPrimaryState    			PrimaryStateValue,
            gslamAGREL50ConcOPVCxSecondaryState  			SecondaryStateValue,
            gslamAGREL50ConcOPVCxProtFunction    			ProtectionEntityValue,
            gslamAGREL50ConcOPVCxSESThreshold    			Unsigned32,     -- SESTH
            gslamAGREL50ConcOPVCxCSESThreshold   			Unsigned32,       -- CSESTH
            gslamAGREL50ConcOPVCxDegMonLev       			Unsigned32,     -- DEGM
            gslamAGREL50ConcOPVCxDegThreshold    			Integer32,        -- DEGTHR
            gslamAGREL50ConcOPVCxOCIProtSwitch   			FlagValue,            -- OCIPS
            gslamAGREL50ConcOPVCxTIMDetectMode   			TIMModeValue,   -- TIMDETM
            gslamAGREL50ConcOPVCxTIMActDisable      		FlagValue,        -- TIMACTDIS
            gslamAGREL50ConcOPVCxExpSAPI            		OCTET STRING,   -- EXPSAPI
            gslamAGREL50ConcOPVCxExpDAPI            		OCTET STRING,   -- EXPDAPI
            gslamAGREL50ConcOPVCxExpOperSpecified   		OCTET STRING,   -- EXPOPR
            gslamAGREL50ConcOPVCxTrcSAPI         			OCTET STRING,   -- TRCSAPI
            gslamAGREL50ConcOPVCxTrcDAPI         			OCTET STRING,   -- TRCDAPI
            gslamAGREL50ConcOPVCxTrcOperSpecified   		OCTET STRING,   -- TRCOPR
            gslamAGREL50ConcOPVCxReceivedTrcSAPI    		OCTET STRING,
            gslamAGREL50ConcOPVCxReceivedTrcDAPI    		OCTET STRING,
            gslamAGREL50ConcOPVCxReceivedTrcOperSpecified   OCTET STRING,
            gslamAGREL50ConcOPVCxExpTrc                     OCTET STRING,   -- EXPTRC
            gslamAGREL50ConcOPVCxTrc                        OCTET STRING,   -- TRC
            gslamAGREL50ConcOPVCxReceivedTrc     			OCTET STRING,    -- INCTRC
            gslamAGREL50ConcOPVCxCRSLpbkType                INTEGER,
            gslamAGREL50ConcOPVCxCRSLpbkDuration            Unsigned32
            -- gslamAGREL50ConcOPVCxRowStatus    			RowStatusValue
            -- gslamAGConcOPVCMasterTimeSlot 				Unsigned32
    }

	gslamAGREL50ConcOPVCxSIndex	OBJECT-TYPE
		SYNTAX		Unsigned32
		MAX-ACCESS	not-accessible
		STATUS		current
		DESCRIPTION
			"Index1 of GSLAM-AG concatenated OPVCxNumic table. It along with the other indices 
			 uniquely identifies each concatenated OPVCxNumic."
    	::= { gslamAGREL50ConcOPVCxEntry 1 }

	gslamAGREL50ConcOPVCxMIndex	OBJECT-TYPE
		SYNTAX		Unsigned32
		MAX-ACCESS	not-accessible
		STATUS		current
		DESCRIPTION
			"Index2 of GSLAM-AG concatenated OPVCxNumic table. It along with the other indices 
			 uniquely identifies each concatenated OPVCxNumic."
    	::= { gslamAGREL50ConcOPVCxEntry 2 }

	gslamAGREL50ConcOPVCxPIndex	OBJECT-TYPE
		SYNTAX		Unsigned32
		MAX-ACCESS	not-accessible
		STATUS		current
		DESCRIPTION
			"Index3 of GSLAM-AG concatenated OPVCxNumic table. It along with the other indices 
			 uniquely identifies each concatenated OPVCxNumic."
    	::= { gslamAGREL50ConcOPVCxEntry 3 }

	gslamAGREL50ConcOPVCxCIndex	OBJECT-TYPE
		SYNTAX		Unsigned32
		MAX-ACCESS	not-accessible
		STATUS		current
		DESCRIPTION
			"Index4 of GSLAM-AG concatenated OPVCxNumic table. It along with the other indices 
			 uniquely identifies each concatenated OPVCxNumic."
    	::= { gslamAGREL50ConcOPVCxEntry 4 }

	gslamAGREL50ConcOPVCxTIndex	OBJECT-TYPE
		SYNTAX		Unsigned32
		MAX-ACCESS	not-accessible
		STATUS		current
		DESCRIPTION
			"Index5 of GSLAM-AG concatenated OPVCxNumic table. It along with the other indices 
			 uniquely identifies each concatenated OPVCxNumic."
    	::= { gslamAGREL50ConcOPVCxEntry 5 }

	gslamAGREL50ConcOPVCxType	OBJECT-TYPE
		SYNTAX		EquipmentTypeValue
		MAX-ACCESS	read-only
		STATUS		current
		DESCRIPTION
			"Indicate the equipment type of this GSLAM-AG concatenated OPVCxNumic."
	::= { gslamAGREL50ConcOPVCxEntry 6 }

    gslamAGREL50ConcOPVCxAction     OBJECT-TYPE
	        SYNTAX      ActionValue
	        MAX-ACCESS  read-write
	        STATUS      current
	        DESCRIPTION
	                "Indicate command issued to this GSLAM-AG concatenated OPVCxNumic."
	::= { gslamAGREL50ConcOPVCxEntry 7 }

	gslamAGREL50ConcOPVCxPrimaryState	OBJECT-TYPE
		SYNTAX	PrimaryStateValue
 	 	MAX-ACCESS  read-write
 	 	STATUS      current
 	 	DESCRIPTION
			"Indicates the primary state of this GSLAM-AG concatenated OPVCxNumic."
  	::= { gslamAGREL50ConcOPVCxEntry 8 }

	gslamAGREL50ConcOPVCxSecondaryState	OBJECT-TYPE
		SYNTAX	SecondaryStateValue
 	 	MAX-ACCESS  read-only
 	 	STATUS      current
 	 	DESCRIPTION
		    "Indicates the secondary state of this GSLAM-AG concatenated
		    OPVCxNumic."
  	::= { gslamAGREL50ConcOPVCxEntry 9 }

	gslamAGREL50ConcOPVCxProtFunction	OBJECT-TYPE
		SYNTAX	ProtectionEntityValue
		MAX-ACCESS  read-only
		STATUS      current
		DESCRIPTION
			"Indicates the protection function of this GSLAM-AG concatenated
			OPVCxNumic."
	::= { gslamAGREL50ConcOPVCxEntry 10 }

	gslamAGREL50ConcOPVCxSESThreshold		OBJECT-TYPE
		SYNTAX	Unsigned32
		MAX-ACCESS  read-write
		STATUS      current
		DESCRIPTION
			"Indicates the severely errored seconds declaration
			threshold value of this GSLAM-AG concatenated OPVCxNumic."
	::= { gslamAGREL50ConcOPVCxEntry 11 }

    gslamAGREL50ConcOPVCxCSESThreshold     OBJECT-TYPE
		SYNTAX  Unsigned32
		MAX-ACCESS  read-write
		STATUS      current
		DESCRIPTION
	    		"Indicates the consecutive signal errored seconds
	    		 declaration threshold value of this GSLAM-AG concatenated OPVCxNumic."
	::= { gslamAGREL50ConcOPVCxEntry 12 }

    gslamAGREL50ConcOPVCxDegMonLev OBJECT-TYPE
		SYNTAX  Unsigned32
		MAX-ACCESS  read-write
		STATUS      current
		DESCRIPTION
	    		"Indicates the degrade monitored level value of this
	    		 GSLAM-AG concatenated OPVCxNumic."
   	::= { gslamAGREL50ConcOPVCxEntry 13 }

  	gslamAGREL50ConcOPVCxDegThreshold  OBJECT-TYPE
		SYNTAX  Integer32
		MAX-ACCESS  read-write
		STATUS      current
		DESCRIPTION
	    		"Indicates the degrade threshold value (percentage of
	    		errored blocks) of this GSLAM-AG concatenated OPVCxNumic. -1 mean not applicable"
	::= { gslamAGREL50ConcOPVCxEntry 14 }

  	gslamAGREL50ConcOPVCxOCIProtSwitch OBJECT-TYPE
		SYNTAX  FlagValue
		MAX-ACCESS  read-write
		STATUS      current
		DESCRIPTION
	    		"Indicates the OCI consequent action value of this
	    		 GSLAM-AG channel."
	::= { gslamAGREL50ConcOPVCxEntry 15 }

   	gslamAGREL50ConcOPVCxTIMDetectMode OBJECT-TYPE
		SYNTAX  TIMModeValue
		MAX-ACCESS  read-write
		STATUS      current
		DESCRIPTION
	    		"Indicates the TIM detection mode value of this
	    		 GSLAM-AG concatenated OPVCxNumic."
	::= { gslamAGREL50ConcOPVCxEntry 16 }

   	gslamAGREL50ConcOPVCxTIMActDisable OBJECT-TYPE
		SYNTAX  FlagValue
		MAX-ACCESS  read-write
		STATUS      current
		DESCRIPTION
	    		"Indicates the TIM consequent action value of this
	    		 GSLAM-AG concatenated OPVCxNumic."
	::= { gslamAGREL50ConcOPVCxEntry 17 }

   	gslamAGREL50ConcOPVCxExpSAPI   OBJECT-TYPE
		SYNTAX      OCTET STRING(SIZE(0..15))
		MAX-ACCESS  read-write
		STATUS      current
		DESCRIPTION
	    		"Indicate the expected SAPI value of this GSLAM-AG
	    		 concatenated OPVCxNumic."
	::= { gslamAGREL50ConcOPVCxEntry 18 }

   	gslamAGREL50ConcOPVCxExpDAPI   OBJECT-TYPE
		SYNTAX      OCTET STRING(SIZE(0..15))
		MAX-ACCESS  read-write
		STATUS      current
		DESCRIPTION
	    		"Indicate the expected DAPI value of this GSLAM-AG
	    		 concatenated OPVCxNumic."
	::= { gslamAGREL50ConcOPVCxEntry 19 }

   	gslamAGREL50ConcOPVCxExpOperSpecified   OBJECT-TYPE
		SYNTAX      OCTET STRING(SIZE(0..32))
		MAX-ACCESS  read-write
		STATUS      current
		DESCRIPTION
		       "Indicate the expected operator specified value of this
	    		GSLAM-AG concatenated OPVCxNumic."
	::= { gslamAGREL50ConcOPVCxEntry 20 }

   	gslamAGREL50ConcOPVCxTrcSAPI   OBJECT-TYPE
		SYNTAX      OCTET STRING(SIZE(0..15))
		MAX-ACCESS  read-write
		STATUS      current
		DESCRIPTION
	    		"Indicate the transmitted SAPI value of this GSLAM-AG
	    		 concatenated OPVCxNumic."
	::= { gslamAGREL50ConcOPVCxEntry 21 }

   	gslamAGREL50ConcOPVCxTrcDAPI   OBJECT-TYPE
		SYNTAX      OCTET STRING(SIZE(0..15))
		MAX-ACCESS  read-write
		STATUS      current
		DESCRIPTION
	    		"Indicate the transmitted DAPI value of this GSLAM-AG
	    		 concatenated OPVCxNumic."
	::= { gslamAGREL50ConcOPVCxEntry 22 }

   	gslamAGREL50ConcOPVCxTrcOperSpecified   OBJECT-TYPE
		SYNTAX      OCTET STRING(SIZE(0..32))
		MAX-ACCESS  read-write
		STATUS      current
		DESCRIPTION
	    		"Indicate the transmitted operator specified value of
	    		 this GSLAM-AG concatenated OPVCxNumic."
	::= { gslamAGREL50ConcOPVCxEntry 23 }

   	gslamAGREL50ConcOPVCxReceivedTrcSAPI   OBJECT-TYPE
		SYNTAX      OCTET STRING(SIZE(0..15))
		MAX-ACCESS  read-only
		STATUS      current
		DESCRIPTION
	    		"Indicate the received SAPI value of this GSLAM-AG
	    		 concatenated OPVCxNumic."
	::= { gslamAGREL50ConcOPVCxEntry 24 }

   	gslamAGREL50ConcOPVCxReceivedTrcDAPI   OBJECT-TYPE
		SYNTAX      OCTET STRING(SIZE(0..15))
		MAX-ACCESS  read-only
		STATUS      current
		DESCRIPTION
	    		"Indicate the received DAPI value of this GSLAM-AG
	    		 concatenated OPVCxNumic."
	::= { gslamAGREL50ConcOPVCxEntry 25 }

   	gslamAGREL50ConcOPVCxReceivedTrcOperSpecified   OBJECT-TYPE
		SYNTAX      OCTET STRING(SIZE(0..32))
		MAX-ACCESS  read-only
		STATUS      current
		DESCRIPTION
	    		"Indicate the received operator specified value of
	    		 this GSLAM-AG concatenated OPVCxNumic."
	::= { gslamAGREL50ConcOPVCxEntry 26 }

	gslamAGREL50ConcOPVCxExpTrc		OBJECT-TYPE
		SYNTAX		OCTET STRING(SIZE(0..64))
		MAX-ACCESS	read-write
		STATUS		current
		DESCRIPTION
			"Indicates the expected trace value of the GSLAM-AG OPVCxNumic channel."
	::= { gslamAGREL50ConcOPVCxEntry 27 }

	gslamAGREL50ConcOPVCxTrc		OBJECT-TYPE
		SYNTAX		OCTET STRING(SIZE(0..64))
		MAX-ACCESS	read-write
		STATUS		current
		DESCRIPTION
			"Indicates the transmitted trace value of the GSLAM-AG
			OPVCxNumic."
	::= { gslamAGREL50ConcOPVCxEntry 28 }

	gslamAGREL50ConcOPVCxReceivedTrc     OBJECT-TYPE
		SYNTAX      OCTET STRING(SIZE(1..64))
		MAX-ACCESS  read-only
		STATUS      current
		DESCRIPTION
	    		"Indicates the received trace value of the GSLAM-AG
	    		OPVCxNumic."
	::= { gslamAGREL50ConcOPVCxEntry 29 }

    gslamAGREL50ConcOPVCxCRSLpbkType     OBJECT-TYPE
    SYNTAX      INTEGER {
        unknown(1),
        not-present(2),
        operate(3),
        release(4)
    }
    MAX-ACCESS  read-write
    STATUS      current
    DESCRIPTION
        "Indicates the cross-connect loopback provisioning for OPVCX channel."
    ::= { gslamAGREL50ConcOPVCxEntry 30 }

    gslamAGREL50ConcOPVCxCRSLpbkDuration     OBJECT-TYPE
    SYNTAX  Unsigned32
    MAX-ACCESS  read-write
    STATUS      current
    DESCRIPTION
        "Indicates the duration of cross-connect loopback."
    ::= { gslamAGREL50ConcOPVCxEntry 31 }

	-- UV 5.0 CHANGE END



	-- concatenated TimeSlot objects
	gslamAGTimeSlotTable		OBJECT-TYPE
		SYNTAX		SEQUENCE OF GslamAGTimeSlotEntry
		MAX-ACCESS	not-accessible
		STATUS		current
		DESCRIPTION
			"A table about the time slot info of GSLAM-AG."
	    ::= { ipiGslamAGTimeSlotObjs 1 }

	gslamAGTimeSlotEntry OBJECT-TYPE
		SYNTAX  		GslamAGTimeSlotEntry
		MAX-ACCESS	not-accessible
		STATUS  		current
		DESCRIPTION
			"A row in TimeSlot table.
			Entries can't be deleted or created via SNMP ops."
		INDEX   { gslamAGShelfIndex, gslamAGIOModuleIndex, gslamAGPortIndex,
			gslamAGChannelIndex, gslamAGTimeSlotIndex  }
	    ::= { gslamAGTimeSlotTable 1 }


	GslamAGTimeSlotEntry ::= SEQUENCE {
		gslamAGTimeSlotIndex		Unsigned32,
		gslamAGConcOPVCxId		Unsigned32,
		gslamAGTimeSlotAvailability             INTEGER

	}

	gslamAGTimeSlotIndex	OBJECT-TYPE
		SYNTAX		Unsigned32
		MAX-ACCESS	read-only
		STATUS		current
		DESCRIPTION
			"It uniquely identifies each TimeSlot in a particular channel."
    	::= { gslamAGTimeSlotEntry 1 }

	gslamAGConcOPVCxId	OBJECT-TYPE
		SYNTAX		Unsigned32
		MAX-ACCESS	read-only
		STATUS		current
		DESCRIPTION
			"Indicate the index of the OPVCX table which is using this timeslot.
			Returns 0 if it does not belong to any OPVCX group."
	    ::= { gslamAGTimeSlotEntry 2 }

	gslamAGTimeSlotAvailability	OBJECT-TYPE
		SYNTAX		INTEGER { unknown(1),available(2),used(3) }
		MAX-ACCESS	read-only
		STATUS		current
		DESCRIPTION
			"Flag to indicate if the timeslot is used during provisioning."
	    ::= { gslamAGTimeSlotEntry 3 }

	-- UV 5.0 START

	-- concatenated TimeSlot objects
	gslamAGREL50TimeSlotTable		OBJECT-TYPE
		SYNTAX		SEQUENCE OF GslamAGREL50TimeSlotEntry
		MAX-ACCESS	not-accessible
		STATUS		current
		DESCRIPTION
			"A table about the time slot info of GSLAM-AG."
	    ::= { ipiGslamAGTimeSlotObjs 2 }

	gslamAGREL50TimeSlotEntry OBJECT-TYPE
		SYNTAX  		GslamAGREL50TimeSlotEntry
		MAX-ACCESS	not-accessible
		STATUS  		current
		DESCRIPTION
			"A row in TimeSlot table.
			Entries can't be deleted or created via SNMP ops."
		INDEX   { gslamAGREL50ShelfIndex, gslamAGREL50IOModuleIndex, gslamAGREL50PortIndex,
			gslamAGREL50ChannelIndex, gslamAGREL50TimeSlotIndex  }
	    ::= { gslamAGREL50TimeSlotTable 1 }


	GslamAGREL50TimeSlotEntry ::= SEQUENCE {
		gslamAGREL50TimeSlotIndex		Unsigned32,
		gslamAGREL50TimeSlotAvailability             INTEGER
	}

	gslamAGREL50TimeSlotIndex	OBJECT-TYPE
		SYNTAX		Unsigned32
		MAX-ACCESS	read-only
		STATUS		current
		DESCRIPTION
			"It uniquely identifies each TimeSlot in a particular channel."
    	::= { gslamAGREL50TimeSlotEntry 1 }

	gslamAGREL50TimeSlotAvailability	OBJECT-TYPE
		SYNTAX		INTEGER { unknown(1),available(2),used(3) }
		MAX-ACCESS	read-only
		STATUS		current
		DESCRIPTION
			"Flag to indicate if the timeslot is used during provisioning."
	    ::= { gslamAGREL50TimeSlotEntry 2 }


	-- UV 5.0 END

	-- ESOM SUPPORT STARTS
	gslamAGSubChannelTable        		OBJECT-TYPE
		SYNTAX             	SEQUENCE OF GslamAGSubChannelEntry
		MAX-ACCESS        	not-accessible
		STATUS                  current
		DESCRIPTION
			"A table about the Sub Channel info"
	::= { ipiGslamAGTimeSlotObjs 3 }

	gslamAGSubChannelEntry         OBJECT-TYPE
		SYNTAX          	GslamAGSubChannelEntry
		MAX-ACCESS        	not-accessible
		STATUS          	current
		DESCRIPTION
			"A row in Sub Channel table, Entries can't be deleted or created via SNMP ops."
		INDEX   {gslamAGShelfIndex, gslamAGIOModuleIndex, gslamAGPortIndex, gslamAGChannelIndex, gslamAGSubChannelIndex}
	::= { gslamAGSubChannelTable 1 }

	GslamAGSubChannelEntry ::= SEQUENCE {
		gslamAGSubChannelIndex                               Unsigned32,
		gslamAGSubChannelIfIndex                             Unsigned32,
		gslamAGSubChannelPrimaryState                        PrimaryStateValue,
		gslamAGSubChannelSecondaryState                      SecondaryStateValue,
		gslamAGSubChannelType                              EquipmentTypeValue 
	}

	gslamAGSubChannelIndex       		OBJECT-TYPE
		SYNTAX                 	Unsigned32
		MAX-ACCESS             	not-accessible
		STATUS                 	current
		DESCRIPTION
		      "Index of Sub Channel table. It uniquely identifies
		      each channel"
		  ::= { gslamAGSubChannelEntry 1 }

	gslamAGSubChannelIfIndex      		 OBJECT-TYPE
		SYNTAX                  Unsigned32
		MAX-ACCESS              read-only
		STATUS                  current
		DESCRIPTION
		      "Indicate the ifIndex of Mib2's interface table of this
		      Sub Channel"
		  ::= { gslamAGSubChannelEntry 2 }

	gslamAGSubChannelPrimaryState        	OBJECT-TYPE
		SYNTAX                  PrimaryStateValue
		MAX-ACCESS              read-only
		STATUS                  current
		DESCRIPTION
		      "Indicates the primary state of this Sub Channel"
		::= { gslamAGSubChannelEntry 3 }


	gslamAGSubChannelSecondaryState        OBJECT-TYPE
		SYNTAX                  SecondaryStateValue
		MAX-ACCESS              read-only
		STATUS                  current
		DESCRIPTION
		      "Indicates the secondary state of this Sub Channel"
		::= { gslamAGSubChannelEntry 4 }

	gslamAGSubChannelType                  OBJECT-TYPE
                SYNTAX                  EquipmentTypeValue 
                MAX-ACCESS              read-only
                STATUS                  current
                DESCRIPTION
                        "Indicates the equipment type of Sub Channel" 
                ::= { gslamAGSubChannelEntry 5 }

		-- UV support                   
	gslamAGREL50SubChannelTable        		OBJECT-TYPE
		SYNTAX             	SEQUENCE OF GslamAGREL50SubChannelEntry
		MAX-ACCESS        	not-accessible
		STATUS                  current
		DESCRIPTION
			"A table about the Sub Channel info"
	::= { ipiGslamAGTimeSlotObjs 4 }

	gslamAGREL50SubChannelEntry         OBJECT-TYPE
		SYNTAX          	GslamAGREL50SubChannelEntry
		MAX-ACCESS        	not-accessible
		STATUS          	current
		DESCRIPTION
			"A row in Sub Channel table, Entries can't be deleted or created via SNMP ops."
		INDEX   {gslamAGREL50ShelfIndex, gslamAGREL50IOModuleIndex, gslamAGREL50PortIndex, gslamAGREL50ChannelIndex, gslamAGREL50SubChannelIndex}
	::= { gslamAGREL50SubChannelTable 1 }

	GslamAGREL50SubChannelEntry ::= SEQUENCE {
		gslamAGREL50SubChannelIndex                               Unsigned32,
		gslamAGREL50SubChannelPrimaryState                        PrimaryStateValue,
		gslamAGREL50SubChannelSecondaryState                      SecondaryStateValue,
		gslamAGREL50SubChannelType                                EquipmentTypeValue 
	}

	gslamAGREL50SubChannelIndex       		OBJECT-TYPE
		SYNTAX                 	Unsigned32
		MAX-ACCESS             	not-accessible
		STATUS                 	current
		DESCRIPTION
		      "Index of Sub Channel table. It uniquely identifies
		      each channel"
		  ::= { gslamAGREL50SubChannelEntry 1 }

	gslamAGREL50SubChannelPrimaryState        	OBJECT-TYPE
		SYNTAX                  PrimaryStateValue
		MAX-ACCESS              read-only
		STATUS                  current
		DESCRIPTION
		      "Indicates the primary state of this Sub Channel"
		::= { gslamAGREL50SubChannelEntry 2 }


	gslamAGREL50SubChannelSecondaryState        OBJECT-TYPE
		SYNTAX                  SecondaryStateValue
		MAX-ACCESS              read-only
		STATUS                  current
		DESCRIPTION
		      "Indicates the secondary state of this Sub Channel"
		::= { gslamAGREL50SubChannelEntry 3 }

	gslamAGREL50SubChannelType                  OBJECT-TYPE
                SYNTAX                  EquipmentTypeValue
                MAX-ACCESS              read-only
                STATUS                  current
                DESCRIPTION
                        "Indicates the equipment type of Sub Channel"
                ::= { gslamAGREL50SubChannelEntry 4 }

	-- ESOM SUPPORT ENDS

   -- GSLAM-AG fabric connection objects.
	gslamAGFabricConnectionTable		OBJECT-TYPE
		SYNTAX		SEQUENCE OF GslamAGFabricConnectionEntry
		MAX-ACCESS	not-accessible
		STATUS		current
		DESCRIPTION
			"A table about the all the fabric connection of GSLAM-AG."
	    ::= { ipiGslamAGFabricConnectionObjs 1 }

	gslamAGFabricConnectionEntry OBJECT-TYPE
		SYNTAX  		GslamAGFabricConnectionEntry
		MAX-ACCESS	not-accessible
		STATUS  		current
		DESCRIPTION
			"A row in the GSLAM-AG fabric connection table."
		INDEX   { gslamAGFabricConnectionFromIfIndex, gslamAGFabricConnectionToIfIndex }
	    ::= { gslamAGFabricConnectionTable 1 }

	GslamAGFabricConnectionEntry ::= SEQUENCE {
		gslamAGFabricConnectionFromIfIndex	Unsigned32,
		gslamAGFabricConnectionToIfIndex	Unsigned32,
		gslamAGFabricConnectionRowStatus	RowStatus,
		gslamAGFabricConnectionDirection	ConnModeValue,
		gslamAGFabricConnectionCktID		OCTET STRING,
		gslamAGFabricConnectionLPID			OCTET STRING
	}

	gslamAGFabricConnectionFromIfIndex		OBJECT-TYPE
		SYNTAX		Unsigned32
		MAX-ACCESS	not-accessible
		STATUS		current
		DESCRIPTION
			"The first index of GSLAM-AG fabric connection table. It indicates
			the 'from' part of ifIndex in the fabric connection."
	    ::= { gslamAGFabricConnectionEntry 1 }

	gslamAGFabricConnectionToIfIndex		OBJECT-TYPE
		SYNTAX		Unsigned32
		MAX-ACCESS	not-accessible
		STATUS		current
		DESCRIPTION
			"The second index of GSLAM-AG fabric connection table. It indicates
			the 'to' part of ifIndex in the fabric connection. Each ifIndex is a 32-bit
			unsigned integer. From left (most significant) to right, we allocate 4
			bits for unit(shelf) id, 4 bits for IO module id, 4 bits for interface(port)
			id, 4 bits for channel id, and the rest (rightmost) 16 bits for OPVC group."
	    ::= { gslamAGFabricConnectionEntry 2 }

	gslamAGFabricConnectionRowStatus		OBJECT-TYPE
		SYNTAX		RowStatus
		MAX-ACCESS	read-create
		STATUS		current
		DESCRIPTION
			"Current status of this GSLAM-AG fabric connection entry."
	    ::= { gslamAGFabricConnectionEntry 3 }

	gslamAGFabricConnectionDirection	OBJECT-TYPE
		SYNTAX	ConnModeValue
 	 	MAX-ACCESS  read-write
 	 	STATUS      current
 	 	DESCRIPTION
			"Indicates the direction of this fabric connection. For unidirection, traffic goes
				from 'from' to 'to'. Default value is bidirection"
 	 	::= { gslamAGFabricConnectionEntry 4 }

	gslamAGFabricConnectionCktID		OBJECT-TYPE
		SYNTAX		OCTET STRING(SIZE(0..64))
		MAX-ACCESS	read-write
		STATUS		current
		DESCRIPTION
			"The connection ID management application using for creating this connection, Return empty string if not available."
	    ::= { gslamAGFabricConnectionEntry 5 }

	gslamAGFabricConnectionLPID		OBJECT-TYPE
		SYNTAX		OCTET STRING(SIZE(0..64))
		MAX-ACCESS	read-write
		STATUS		current
		DESCRIPTION
			"The light path ID management application enters when creating this connection, Return empty string if not available."
	    ::= { gslamAGFabricConnectionEntry 6 }

	-- UV 5.0 CHANGE START 
	-- Fabric Cross Connect

	gslamAGREL50FabricCXTable		OBJECT-TYPE
		SYNTAX		SEQUENCE OF GslamAGREL50FabricCXEntry
		MAX-ACCESS	not-accessible
		STATUS		current
		DESCRIPTION
			"A table about the all the fabric ConnectionNumic of GSLAM-AG."
	    ::= { ipiGslamAGFabricConnectionObjs 2 }

	gslamAGREL50FabricCXEntry OBJECT-TYPE
		SYNTAX  		GslamAGREL50FabricCXEntry
		MAX-ACCESS		not-accessible
		STATUS  		current
		DESCRIPTION
			"A row in the GSLAM-AG fabric ConnectionNumic table."
		INDEX   { 	gslamAGREL50FabricCXFromSIndex,gslamAGREL50FabricCXFromMIndex,
			  		gslamAGREL50FabricCXFromPIndex,gslamAGREL50FabricCXFromCIndex,
			  		gslamAGREL50FabricCXFromTIndex,gslamAGREL50FabricCXToSIndex,
			  		gslamAGREL50FabricCXToMIndex,gslamAGREL50FabricCXToPIndex,
			  		gslamAGREL50FabricCXToCIndex,gslamAGREL50FabricCXToTIndex}
	    ::= { gslamAGREL50FabricCXTable 1 }

	GslamAGREL50FabricCXEntry ::= SEQUENCE {
		gslamAGREL50FabricCXFromSIndex      Unsigned32,
       	gslamAGREL50FabricCXFromMIndex      Unsigned32,
        gslamAGREL50FabricCXFromPIndex      Unsigned32,
        gslamAGREL50FabricCXFromCIndex      Unsigned32,
        gslamAGREL50FabricCXFromTIndex      Unsigned32,
		gslamAGREL50FabricCXToSIndex        Unsigned32,
        gslamAGREL50FabricCXToMIndex        Unsigned32,
        gslamAGREL50FabricCXToPIndex        Unsigned32,
        gslamAGREL50FabricCXToCIndex        Unsigned32,
        gslamAGREL50FabricCXToTIndex        Unsigned32,
		gslamAGREL50FabricCXRowStatus       RowStatus,
		gslamAGREL50FabricCXDirection	    ConnModeValue,
		gslamAGREL50FabricCXCktID		    OCTET STRING,
		gslamAGREL50FabricCXLPID		    OCTET STRING
	}

	gslamAGREL50FabricCXFromSIndex		OBJECT-TYPE
		SYNTAX		Unsigned32
		MAX-ACCESS	not-accessible
		STATUS		current
		DESCRIPTION
			"Index1 of GSLAM-AG GslamAGREL50FabricCXEntry table. 
			 It indicates shelf index of
			 the 'from' part of ifIndex in the fabric ConnectionNumic."
	    ::= { gslamAGREL50FabricCXEntry 1 }

	gslamAGREL50FabricCXFromMIndex		OBJECT-TYPE
		SYNTAX		Unsigned32
		MAX-ACCESS	not-accessible
		STATUS		current
		DESCRIPTION
			"Index2 of GSLAM-AG fabric ConnectionNumic table. It indicates module index of
			the 'from' part of ifIndex in the fabric ConnectionNumic."
	    ::= { gslamAGREL50FabricCXEntry 2 }

	gslamAGREL50FabricCXFromPIndex			OBJECT-TYPE
		SYNTAX		Unsigned32
		MAX-ACCESS	not-accessible
		STATUS		current
		DESCRIPTION
			"Index3 of GSLAM-AG fabric ConnectionNumic table. It indicates port index of
			the 'from' part of ifIndex in the fabric ConnectionNumic."
	    ::= { gslamAGREL50FabricCXEntry 3 }

	gslamAGREL50FabricCXFromCIndex			OBJECT-TYPE
		SYNTAX		Unsigned32
		MAX-ACCESS	not-accessible
		STATUS		current
		DESCRIPTION
			"Index4 of GSLAM-AG fabric ConnectionNumic table. It indicates chnl index of
			the 'from' part of ifIndex in the fabric ConnectionNumic."
	    ::= { gslamAGREL50FabricCXEntry 4 }

	gslamAGREL50FabricCXFromTIndex			OBJECT-TYPE
		SYNTAX		Unsigned32
		MAX-ACCESS	not-accessible
		STATUS		current
		DESCRIPTION
			"Index5 of GSLAM-AG fabric ConnectionNumic table. 
			It indicates ts index of
			the 'from' part of ifIndex in the fabric ConnectionNumic.
			It is a bit-encoded entity and '1' represents that TS is present
			and '0' represents not present."
	    ::= { gslamAGREL50FabricCXEntry 5 }

	gslamAGREL50FabricCXToSIndex			OBJECT-TYPE
		SYNTAX		Unsigned32
		MAX-ACCESS	not-accessible
		STATUS		current
		DESCRIPTION
			"Index1 of GSLAM-AG fabric ConnectionNumic table. It indicates shelf index of
			the 'to' part of ifIndex in the fabric ConnectionNumic."
	    ::= { gslamAGREL50FabricCXEntry 6 }

	gslamAGREL50FabricCXToMIndex			OBJECT-TYPE
		SYNTAX		Unsigned32
		MAX-ACCESS	not-accessible
		STATUS		current
		DESCRIPTION
			"Index2 of GSLAM-AG fabric ConnectionNumic table. It indicates Module index of
			the 'to' part of ifIndex in the fabric ConnectionNumic."
	    ::= { gslamAGREL50FabricCXEntry 7 }

	gslamAGREL50FabricCXToPIndex			OBJECT-TYPE
		SYNTAX		Unsigned32
		MAX-ACCESS	not-accessible
		STATUS		current
		DESCRIPTION
			"Index3 of GSLAM-AG fabric ConnectionNumic table. It indicates port index of
			the 'to' part of ifIndex in the fabric ConnectionNumic."
	    ::= { gslamAGREL50FabricCXEntry 8 }

	gslamAGREL50FabricCXToCIndex			OBJECT-TYPE
		SYNTAX		Unsigned32
		MAX-ACCESS	not-accessible
		STATUS		current
		DESCRIPTION
			"Index4 of GSLAM-AG fabric ConnectionNumic table. It indicates chnl index of
			the 'to' part of ifIndex in the fabric ConnectionNumic."
	    ::= { gslamAGREL50FabricCXEntry 9 }

	gslamAGREL50FabricCXToTIndex			OBJECT-TYPE
		SYNTAX		Unsigned32
		MAX-ACCESS	not-accessible
		STATUS		current
		DESCRIPTION
			"Index5 of GSLAM-AG fabric ConnectionNumic table. 
			It indicates ts index of
			the 'to' part of ifIndex in the fabric ConnectionNumic.
			It is a bit-encoded entity and '1' represents that TS is present
            and '0' represents not present."
	    ::= { gslamAGREL50FabricCXEntry 10 }

	gslamAGREL50FabricCXRowStatus			OBJECT-TYPE
		SYNTAX		RowStatus
		MAX-ACCESS	read-create
		STATUS		current
		DESCRIPTION
			"Current status of this GSLAM-AG fabric ConnectionNumic entry."
	    ::= { gslamAGREL50FabricCXEntry 11 }

	gslamAGREL50FabricCXDirection			OBJECT-TYPE
		SYNTAX	ConnModeValue
 	 	MAX-ACCESS  read-write
 	 	STATUS      current
 	 	DESCRIPTION
			"Indicates the direction of this fabric ConnectionNumic. For unidirection, traffic goes
				from 'from' to 'to'. Default value is bidirection"
 	 	::= { gslamAGREL50FabricCXEntry 12 }

	gslamAGREL50FabricCXCktID				OBJECT-TYPE
		SYNTAX		OCTET STRING(SIZE(0..64))
		MAX-ACCESS	read-write
		STATUS		current
		DESCRIPTION
			"The ConnectionNumic ID management application using for creating this ConnectionNumic, 
			 Return empty string if not available."
	    ::= { gslamAGREL50FabricCXEntry 13 }

	gslamAGREL50FabricCXLPID				OBJECT-TYPE
		SYNTAX		OCTET STRING(SIZE(0..64))
		MAX-ACCESS	read-write
		STATUS		current
		DESCRIPTION
			"The light path ID management application enters when creating this ConnectionNumic, 
			 Return empty string if not available."
	    ::= { gslamAGREL50FabricCXEntry 14 }

     -- UV 5.0 CHANGE	END
	
	-- ESOM Logical connection objects.
	gslamAGLogicalConnectionTable		OBJECT-TYPE
		SYNTAX		SEQUENCE OF GslamAGLogicalConnectionEntry
		MAX-ACCESS	not-accessible
		STATUS		current
		DESCRIPTION
			"A table about the all the logical connections of ESOM."
	    ::= { ipiGslamAGLogicalConnectionObjs 1 }

	gslamAGLogicalConnectionEntry OBJECT-TYPE
		SYNTAX  		GslamAGLogicalConnectionEntry
		MAX-ACCESS	not-accessible
		STATUS  		current
		DESCRIPTION
			"A row in the GSLAM-AG fabric connection table."
		INDEX   { gslamAGLogicalConnectionFromIfIndex, gslamAGLogicalConnectionToIfIndex }
	    ::= { gslamAGLogicalConnectionTable 1 }

	GslamAGLogicalConnectionEntry ::= SEQUENCE {
		gslamAGLogicalConnectionFromIfIndex	Unsigned32,
		gslamAGLogicalConnectionToIfIndex	Unsigned32,
		gslamAGLogicalConnectionRowStatus	RowStatus,
		gslamAGLogicalConnectionDirection	ConnModeValue,
		gslamAGLogicalConnectionCktID		OCTET STRING
	}

	gslamAGLogicalConnectionFromIfIndex		OBJECT-TYPE
		SYNTAX		Unsigned32
		MAX-ACCESS	not-accessible
		STATUS		current
		DESCRIPTION
			"The first index of ESOM logical connection table. It indicates
			the 'from' part of ifIndex in the fabric connection."
	    ::= { gslamAGLogicalConnectionEntry 1 }

	gslamAGLogicalConnectionToIfIndex		OBJECT-TYPE
		SYNTAX		Unsigned32
		MAX-ACCESS	not-accessible
		STATUS		current
		DESCRIPTION
			"The second index of ESOM logical connection table. It indicates
			the 'to' part of ifIndex in the logical connection. Each ifIndex is a 32-bit
			unsigned integer. From left (most significant) to right, we allocate 4
			bits for unit(shelf) id, 4 bits for IO module id, 8 bits for interface(port)
			id, 8 bits for channel id, and the rest (rightmost) 8 bits for subchannels."
	    ::= { gslamAGLogicalConnectionEntry 2 }

	gslamAGLogicalConnectionRowStatus		OBJECT-TYPE
		SYNTAX		RowStatus
		MAX-ACCESS	read-create
		STATUS		current
		DESCRIPTION
			"Current status of this ESOM logical connection entry."
	    ::= { gslamAGLogicalConnectionEntry 3 }

	gslamAGLogicalConnectionDirection	OBJECT-TYPE
		SYNTAX	ConnModeValue
 	 	MAX-ACCESS  read-write
 	 	STATUS      current
 	 	DESCRIPTION
			"Indicates the direction of this logical connection. For unidirection, traffic goes
				from 'from' to 'to'. Default value is bidirection"
 	 	::= { gslamAGLogicalConnectionEntry 4 }

	gslamAGLogicalConnectionCktID		OBJECT-TYPE
		SYNTAX		OCTET STRING(SIZE(0..64))
		MAX-ACCESS	read-write
		STATUS		current
		DESCRIPTION
			"The connection ID management application using for creating this connection, Return empty string if not available."
	    ::= { gslamAGLogicalConnectionEntry 5 }

	
	-- UV 5.0 CHANGE START 
	-- ESOM Logical Cross Connect

	gslamAGREL50LogicalCXTable		OBJECT-TYPE
		SYNTAX		SEQUENCE OF GslamAGREL50LogicalCXEntry
		MAX-ACCESS	not-accessible
		STATUS		current
		DESCRIPTION
			"A table about the all the logical connection Numic of ESOM."
	    ::= { ipiGslamAGLogicalConnectionObjs 2 }

	gslamAGREL50LogicalCXEntry OBJECT-TYPE
		SYNTAX  		GslamAGREL50LogicalCXEntry
		MAX-ACCESS		not-accessible
		STATUS  		current
		DESCRIPTION
			"A row in the ESOM logicalConnection Numic table."
		INDEX   { 	gslamAGREL50LogicalCXFromSIndex,gslamAGREL50LogicalCXFromMIndex,
			  		gslamAGREL50LogicalCXFromPIndex,gslamAGREL50LogicalCXFromCIndex,
			  		gslamAGREL50LogicalCXFromTIndex,gslamAGREL50LogicalCXToSIndex,
			  		gslamAGREL50LogicalCXToMIndex,gslamAGREL50LogicalCXToPIndex,
			  		gslamAGREL50LogicalCXToCIndex,gslamAGREL50LogicalCXToTIndex}
	    ::= { gslamAGREL50LogicalCXTable 1 }

	GslamAGREL50LogicalCXEntry ::= SEQUENCE {
		gslamAGREL50LogicalCXFromSIndex      Unsigned32,
		gslamAGREL50LogicalCXFromMIndex      Unsigned32,
		gslamAGREL50LogicalCXFromPIndex      Unsigned32,
		gslamAGREL50LogicalCXFromCIndex      Unsigned32,
		gslamAGREL50LogicalCXFromTIndex      Unsigned32,
		gslamAGREL50LogicalCXToSIndex        Unsigned32,
	        gslamAGREL50LogicalCXToMIndex        Unsigned32,
	        gslamAGREL50LogicalCXToPIndex        Unsigned32,
	        gslamAGREL50LogicalCXToCIndex        Unsigned32,
	        gslamAGREL50LogicalCXToTIndex        Unsigned32,
		gslamAGREL50LogicalCXRowStatus       RowStatus,
		gslamAGREL50LogicalCXDirection	    ConnModeValue,
		gslamAGREL50LogicalCXCktID		    OCTET STRING
		}

	gslamAGREL50LogicalCXFromSIndex		OBJECT-TYPE
		SYNTAX		Unsigned32
		MAX-ACCESS	not-accessible
		STATUS		current
		DESCRIPTION
			"Index 1 of ESOM GslamAGREL50LogicalCXEntry table. 
			 It indicates shelf index of
			 the 'from' part of ifIndex in the logical ConnectionNumic."
	    ::= { gslamAGREL50LogicalCXEntry 1 }

	gslamAGREL50LogicalCXFromMIndex		OBJECT-TYPE
		SYNTAX		Unsigned32
		MAX-ACCESS	not-accessible
		STATUS		current
		DESCRIPTION
			"Index2 of ESOM logical ConnectionNumic table. It indicates module index of
			the 'from' part of ifIndex in the logical ConnectionNumic."
	    ::= { gslamAGREL50LogicalCXEntry 2 }

	gslamAGREL50LogicalCXFromPIndex			OBJECT-TYPE
		SYNTAX		Unsigned32
		MAX-ACCESS	not-accessible
		STATUS		current
		DESCRIPTION
			"Index3 of ESOM logical ConnectionNumic table. It indicates port index of
			the 'from' part of ifIndex in the logical ConnectionNumic."
	    ::= { gslamAGREL50LogicalCXEntry 3 }

	gslamAGREL50LogicalCXFromCIndex			OBJECT-TYPE
		SYNTAX		Unsigned32
		MAX-ACCESS	not-accessible
		STATUS		current
		DESCRIPTION
			"Index4 of ESOM logical ConnectionNumic table. It indicates chnl index of
			the 'from' part of ifIndex in the logical ConnectionNumic."
	    ::= { gslamAGREL50LogicalCXEntry 4 }

	gslamAGREL50LogicalCXFromTIndex			OBJECT-TYPE
		SYNTAX		Unsigned32
		MAX-ACCESS	not-accessible
		STATUS		current
		DESCRIPTION
			"Index5 of ESOM logical ConnectionNumic table. 
			It indicates ts index of
			the 'from' part of ifIndex in the logical ConnectionNumic.
			It is a bit-encoded entity and '1' represents that TS is present
			and '0' represents not present."
	    ::= { gslamAGREL50LogicalCXEntry 5 }

	gslamAGREL50LogicalCXToSIndex			OBJECT-TYPE
		SYNTAX		Unsigned32
		MAX-ACCESS	not-accessible
		STATUS		current
		DESCRIPTION
			"Index1 of ESOM logical ConnectionNumic table. It indicates shelf index of
			the 'to' part of ifIndex in the logical ConnectionNumic."
	    ::= { gslamAGREL50LogicalCXEntry 6 }

	gslamAGREL50LogicalCXToMIndex			OBJECT-TYPE
		SYNTAX		Unsigned32
		MAX-ACCESS	not-accessible
		STATUS		current
		DESCRIPTION
			"Index2 of ESOM logical ConnectionNumic table. It indicates Module index of
			the 'to' part of ifIndex in the logical ConnectionNumic."
	    ::= { gslamAGREL50LogicalCXEntry 7 }

	gslamAGREL50LogicalCXToPIndex			OBJECT-TYPE
		SYNTAX		Unsigned32
		MAX-ACCESS	not-accessible
		STATUS		current
		DESCRIPTION
			"Index3 of ESOM logicalConnectionNumic table. It indicates port index of
			the 'to' part of ifIndex in the fabric ConnectionNumic."
	    ::= { gslamAGREL50LogicalCXEntry 8 }

	gslamAGREL50LogicalCXToCIndex			OBJECT-TYPE
		SYNTAX		Unsigned32
		MAX-ACCESS	not-accessible
		STATUS		current
		DESCRIPTION
			"Index4 of ESOM logical ConnectionNumic table. It indicates chnl index of
			the 'to' part of ifIndex in the logical ConnectionNumic."
	    ::= { gslamAGREL50LogicalCXEntry 9 }

	gslamAGREL50LogicalCXToTIndex			OBJECT-TYPE
		SYNTAX		Unsigned32
		MAX-ACCESS	not-accessible
		STATUS		current
		DESCRIPTION
			"Index5 of ESOM logical ConnectionNumic table. 
			It indicates ts index of
			the 'to' part of ifIndex in the logical ConnectionNumic."
	    ::= { gslamAGREL50LogicalCXEntry 10 }

	gslamAGREL50LogicalCXRowStatus			OBJECT-TYPE
		SYNTAX		RowStatus
		MAX-ACCESS	read-create
		STATUS		current
		DESCRIPTION
			"Current status of this ESOM logical ConnectionNumic entry."
	    ::= { gslamAGREL50LogicalCXEntry 11 }

	gslamAGREL50LogicalCXDirection			OBJECT-TYPE
		SYNTAX	ConnModeValue
 	 	MAX-ACCESS  read-write
 	 	STATUS      current
 	 	DESCRIPTION
			"Indicates the direction of this logical ConnectionNumic. For unidirection, traffic goes
				from 'from' to 'to'. Default value is bidirection"
 	 	::= { gslamAGREL50LogicalCXEntry 12 }

	gslamAGREL50LogicalCXCktID				OBJECT-TYPE
		SYNTAX		OCTET STRING(SIZE(0..64))
		MAX-ACCESS	read-write
		STATUS		current
		DESCRIPTION
			"The ConnectionNumic ID management application using for creating this ConnectionNumic, 
			 Return empty string if not available."
	    ::= { gslamAGREL50LogicalCXEntry 13 }

     -- UV 5.0 CHANGE	END
     
   -- GSLAM-AG neighbor connection objects.
	gslamAGExternalConnectionTable		OBJECT-TYPE
		SYNTAX		SEQUENCE OF GslamAGExternalConnectionEntry
		MAX-ACCESS	not-accessible
		STATUS		current
		DESCRIPTION
			"A table about the all the neighbor connection info of GSLAM-AG."
	    ::= { ipiGslamAGExternalConnectionObjs 1}

	gslamAGExternalConnectionEntry OBJECT-TYPE
		SYNTAX  		GslamAGExternalConnectionEntry
		MAX-ACCESS	not-accessible
		STATUS  		current
		DESCRIPTION
			"A row in the GSLAM-AG neighbor connection table.
			Entries can't be deleted or created via SNMP ops."
		INDEX   { gslamAGShelfIndex, gslamAGIOModuleIndex, gslamAGPortIndex }
	    ::= { gslamAGExternalConnectionTable 1}

	GslamAGExternalConnectionEntry ::= SEQUENCE {
		gslamAGExternalConnectionLocalIP	IpAddress,
		gslamAGExternalConnectionLocalUMIC	UMICValue,
		gslamAGExternalConnectionRemoteNodeIP	IpAddress,
		gslamAGExternalConnectionRemoteIP	IpAddress,
		gslamAGExternalConnectionRemoteUMIC	UMICValue,
		gslamAGExternalConnectionRemoteNodeType	RemoteNodeTypeValue,
		gslamAGExternalConnectionLocalNodeTID	OCTET STRING,
		gslamAGExternalConnectionRemoteNodeTID	OCTET STRING,
		gslamAGExternalConnectionStatus		INTEGER,
		gslamAGExternalConnectionType		INTEGER,
		gslamAGExternalConnectionRemotePortAID	OCTET STRING
	}


	gslamAGExternalConnectionLocalIP		OBJECT-TYPE
		SYNTAX		IpAddress
		MAX-ACCESS	read-only
		STATUS		current
		DESCRIPTION
			"Indicates the IP address of the local end of this external connection."
	    ::= { gslamAGExternalConnectionEntry 1 }

	gslamAGExternalConnectionLocalUMIC		OBJECT-TYPE
		SYNTAX		UMICValue
		MAX-ACCESS	read-only
		STATUS		current
		DESCRIPTION
			"Indicates the UMIC value of the local end of this external connection."
	    ::= { gslamAGExternalConnectionEntry 2 }

	gslamAGExternalConnectionRemoteNodeIP		OBJECT-TYPE
		SYNTAX		IpAddress
		MAX-ACCESS	read-only
		STATUS		current
		DESCRIPTION
			"Indicates the IP address of the remote node of this external connection."
	    ::= { gslamAGExternalConnectionEntry 3 }

	gslamAGExternalConnectionRemoteIP	OBJECT-TYPE
		SYNTAX		IpAddress
		MAX-ACCESS	read-only
		STATUS		current
		DESCRIPTION
			"Indicates the IP address of the remote end of this external connection."
	    ::= { gslamAGExternalConnectionEntry 4 }

	gslamAGExternalConnectionRemoteUMIC	OBJECT-TYPE
		SYNTAX		UMICValue
		MAX-ACCESS	read-only
		STATUS		current
		DESCRIPTION
			"Indicates the UMIC value of the remote end of this external connection."
	    ::= { gslamAGExternalConnectionEntry 5 }

	gslamAGExternalConnectionRemoteNodeType		OBJECT-TYPE
		SYNTAX		RemoteNodeTypeValue
		MAX-ACCESS	read-only
		STATUS		current
		DESCRIPTION
			"Indicates the equiptment type of the remote end of this external connection."
	    ::= { gslamAGExternalConnectionEntry 6 }

	gslamAGExternalConnectionLocalNodeTID		OBJECT-TYPE
		SYNTAX		OCTET STRING(SIZE(1..20))
		MAX-ACCESS	read-only
		STATUS		current
		DESCRIPTION
			"Indicates the TID of the local end of this external connection."
	    ::= { gslamAGExternalConnectionEntry 7 }

	gslamAGExternalConnectionRemoteNodeTID		OBJECT-TYPE
		SYNTAX		OCTET STRING(SIZE(1..20))
		MAX-ACCESS	read-only
		STATUS		current
		DESCRIPTION
			"Indicates the TID of the remote end of this external connection."
	    ::= { gslamAGExternalConnectionEntry 8 }

	gslamAGExternalConnectionStatus	OBJECT-TYPE
		SYNTAX INTEGER {
			unknown(1),
			ndp-enabled(2),
			admin-enabled(3)
		}
		MAX-ACCESS	read-only
		STATUS		current
		DESCRIPTION
			"Used to indicate if the connection is ndp or admin enabled."
	    ::= { gslamAGExternalConnectionEntry 9 }

	gslamAGExternalConnectionType	OBJECT-TYPE
		SYNTAX INTEGER {
			unknown(1),
			not-applicable(2),
			external(3),
			optical(4)
		}
		MAX-ACCESS	read-only
		STATUS		current
		DESCRIPTION
			"Used to indicate the connection type, if its optical connection ot not."
	    ::= { gslamAGExternalConnectionEntry 10 }

	gslamAGExternalConnectionRemotePortAID		OBJECT-TYPE
		SYNTAX		OCTET STRING(SIZE(1..20))
		MAX-ACCESS	read-only
		STATUS		current
		DESCRIPTION
			"Indicates the AID of the remote end port of this external connection."
	    ::= { gslamAGExternalConnectionEntry 11 }

	-- UV 5.0 start

    -- GSLAM-AG neighbor connection objects.
	gslamAGREL50ExtCXTable		OBJECT-TYPE
		SYNTAX		SEQUENCE OF GslamAGREL50ExtCXEntry
		MAX-ACCESS	not-accessible
		STATUS		current
		DESCRIPTION
			"A table about the all the neighbor connection info of GSLAM-AG."
	    ::= { ipiGslamAGExternalConnectionObjs 2}

	gslamAGREL50ExtCXEntry OBJECT-TYPE
		SYNTAX  		GslamAGREL50ExtCXEntry
		MAX-ACCESS	not-accessible
		STATUS  		current
		DESCRIPTION
			"A row in the GSLAM-AG neighbor connection table.
			Entries can't be deleted or created via SNMP ops."
		INDEX   { gslamAGREL50ShelfIndex, gslamAGREL50IOModuleIndex, gslamAGREL50PortIndex }
	    ::= { gslamAGREL50ExtCXTable 1}

	GslamAGREL50ExtCXEntry ::= SEQUENCE {
		gslamAGREL50ExtCXLocalIP	IpAddress,
		gslamAGREL50ExtCXLocalShelf	Unsigned32,
		gslamAGREL50ExtCXLocalMod		Unsigned32,
		gslamAGREL50ExtCXLocalPort		Unsigned32,
		gslamAGREL50ExtCXRemoteNodeIP	IpAddress,
		gslamAGREL50ExtCXRemoteIP	IpAddress,
		gslamAGREL50ExtCXRemoteShelf	Unsigned32,
		gslamAGREL50ExtCXRemoteMod		Unsigned32,
		gslamAGREL50ExtCXRemotePort	Unsigned32,
		gslamAGREL50ExtCXRemoteNodeType	RemoteNodeTypeValue,
		gslamAGREL50ExtCXLocalNodeTID	OCTET STRING,
		gslamAGREL50ExtCXRemoteNodeTID	OCTET STRING,
		gslamAGREL50ExtCXStatus		INTEGER,
		gslamAGREL50ExtCXType		INTEGER,
		gslamAGREL50ExtCXRemotePortAID	OCTET STRING
	}


	gslamAGREL50ExtCXLocalIP		OBJECT-TYPE
		SYNTAX		IpAddress
		MAX-ACCESS	read-only
		STATUS		current
		DESCRIPTION
			"Indicates the IP address of the local end of this external connection."
	    ::= { gslamAGREL50ExtCXEntry 1 }

	gslamAGREL50ExtCXLocalShelf		OBJECT-TYPE
		SYNTAX		Unsigned32
		MAX-ACCESS	read-only
		STATUS		current
		DESCRIPTION
			"Indicates the shelf value of the local end of this external connection."
	    ::= { gslamAGREL50ExtCXEntry 2 }

	gslamAGREL50ExtCXLocalMod		OBJECT-TYPE
		SYNTAX		Unsigned32
		MAX-ACCESS	read-only
		STATUS		current
		DESCRIPTION
			"Indicates the module value of the local end of this external connection."
	    ::= { gslamAGREL50ExtCXEntry 3 }

	gslamAGREL50ExtCXLocalPort		OBJECT-TYPE
		SYNTAX		Unsigned32
		MAX-ACCESS	read-only
		STATUS		current
		DESCRIPTION
			"Indicates the Port value of the local end of this external connection."
	    ::= { gslamAGREL50ExtCXEntry 4 }

	gslamAGREL50ExtCXRemoteNodeIP		OBJECT-TYPE
		SYNTAX		IpAddress
		MAX-ACCESS	read-only
		STATUS		current
		DESCRIPTION
			"Indicates the IP address of the remote node of this external connection."
	    ::= { gslamAGREL50ExtCXEntry 5 }

	gslamAGREL50ExtCXRemoteIP	OBJECT-TYPE
		SYNTAX		IpAddress
		MAX-ACCESS	read-only
		STATUS		current
		DESCRIPTION
			"Indicates the IP address of the remote end of this external connection."
	    ::= { gslamAGREL50ExtCXEntry 6 }

	gslamAGREL50ExtCXRemoteShelf		OBJECT-TYPE
		SYNTAX		Unsigned32
		MAX-ACCESS	read-only
		STATUS		current
		DESCRIPTION
			"Indicates the shelf value of the Remote end of this external connection."
	    ::= { gslamAGREL50ExtCXEntry 7 }

	gslamAGREL50ExtCXRemoteMod		OBJECT-TYPE
		SYNTAX		Unsigned32
		MAX-ACCESS	read-only
		STATUS		current
		DESCRIPTION
			"Indicates the module value of the Remote end of this external connection."
	    ::= { gslamAGREL50ExtCXEntry 8 }

	gslamAGREL50ExtCXRemotePort		OBJECT-TYPE
		SYNTAX		Unsigned32
		MAX-ACCESS	read-only
		STATUS		current
		DESCRIPTION
			"Indicates the Port value of the Remote end of this external connection."
	    ::= { gslamAGREL50ExtCXEntry 9 }

	gslamAGREL50ExtCXRemoteNodeType		OBJECT-TYPE
		SYNTAX		RemoteNodeTypeValue
		MAX-ACCESS	read-only
		STATUS		current
		DESCRIPTION
			"Indicates the equiptment type of the remote end of this external connection."
	    ::= { gslamAGREL50ExtCXEntry 10 }

	gslamAGREL50ExtCXLocalNodeTID		OBJECT-TYPE
		SYNTAX		OCTET STRING(SIZE(1..20))
		MAX-ACCESS	read-only
		STATUS		current
		DESCRIPTION
			"Indicates the TID of the local end of this external connection."
	    ::= { gslamAGREL50ExtCXEntry 11 }

	gslamAGREL50ExtCXRemoteNodeTID		OBJECT-TYPE
		SYNTAX		OCTET STRING(SIZE(1..20))
		MAX-ACCESS	read-only
		STATUS		current
		DESCRIPTION
			"Indicates the TID of the remote end of this external connection."
	    ::= { gslamAGREL50ExtCXEntry 12 }

	gslamAGREL50ExtCXStatus	OBJECT-TYPE
		SYNTAX INTEGER {
			unknown(1),
			ndp-enabled(2),
			admin-enabled(3)
		}
		MAX-ACCESS	read-only
		STATUS		current
		DESCRIPTION
			"Used to indicate if the connection is ndp or admin enabled."
	    ::= { gslamAGREL50ExtCXEntry 13 }

	gslamAGREL50ExtCXType	OBJECT-TYPE
		SYNTAX INTEGER {
			unknown(1),
			not-applicable(2),
			external(3),
			optical(4)
		}
		MAX-ACCESS	read-only
		STATUS		current
		DESCRIPTION
			"Used to indicate the connection type, if its optical connection ot not."
	    ::= { gslamAGREL50ExtCXEntry 14 }

	gslamAGREL50ExtCXRemotePortAID		OBJECT-TYPE
		SYNTAX		OCTET STRING(SIZE(1..20))
		MAX-ACCESS	read-only
		STATUS		current
		DESCRIPTION
			"Indicates the AID of the remote end of this external connection."
	    ::= { gslamAGREL50ExtCXEntry 15 }

	-- UV 5.0 end

     -- GSLAM-AG facility/path protection group objects.
	gslamAGProtectionGroupTable		OBJECT-TYPE
		SYNTAX		SEQUENCE OF GslamAGProtectionGroupEntry
		MAX-ACCESS	not-accessible
		STATUS		current
		DESCRIPTION
			"A table about the facility/path protection group of GSLAM-AG."
	    ::= { ipiGslamAGProtectionGroupObjs 1 }

	gslamAGProtectionGroupEntry OBJECT-TYPE
		SYNTAX  		GslamAGProtectionGroupEntry
		MAX-ACCESS	not-accessible
		STATUS  		current
		DESCRIPTION
			"A row in the GSLAM-AG protection group table."
		INDEX   { gslamAGProtectionGroupProtectedIndex, gslamAGProtectionGroupProtectingIndex }
	    ::= { gslamAGProtectionGroupTable 1 }

	GslamAGProtectionGroupEntry ::= SEQUENCE {
		gslamAGProtectionGroupProtectedIndex	Unsigned32,
		gslamAGProtectionGroupProtectingIndex	Unsigned32,
		gslamAGProtectionGroupRowStatus		RowStatus,
		gslamAGProtectionGroupSwitchType	ProtectionSwitchTypeValue,
		gslamAGProtectionGroupSwitchDir		ProtectionSwitchDirValue,
		gslamAGProtectionGroupRvrt		FlagValue,
		gslamAGProtectionGroupLPID		OCTET STRING,
		gslamAGProtectionGroupSwitchCmd		ProtectionSwitchCmdValue,
		gslamAGProtectionGroupActiveIndex	Unsigned32
	}

	gslamAGProtectionGroupProtectedIndex		OBJECT-TYPE
		SYNTAX		Unsigned32
		MAX-ACCESS	not-accessible
		STATUS		current
		DESCRIPTION
			"The index value of the first entity (port, channel or opvcx) in the protection group."
	    ::= { gslamAGProtectionGroupEntry 1 }

	gslamAGProtectionGroupProtectingIndex		OBJECT-TYPE
		SYNTAX		Unsigned32
		MAX-ACCESS	not-accessible
		STATUS		current
		DESCRIPTION
			"The index value of the second entity (port, channel or opvcx) in the protection group."
	    ::= { gslamAGProtectionGroupEntry 2 }


	gslamAGProtectionGroupRowStatus		OBJECT-TYPE
		SYNTAX		RowStatus
		MAX-ACCESS	read-create
		STATUS		current
		DESCRIPTION
			"Current status of this protection group entry."
	    ::= { gslamAGProtectionGroupEntry 3 }

	gslamAGProtectionGroupSwitchType		OBJECT-TYPE
		SYNTAX		ProtectionSwitchTypeValue
		MAX-ACCESS	read-only
		STATUS		current
		DESCRIPTION
			"Indicate the protection switch type of this protection entry."
	    ::= { gslamAGProtectionGroupEntry 4 }

	gslamAGProtectionGroupSwitchDir		OBJECT-TYPE
		SYNTAX		ProtectionSwitchDirValue
		MAX-ACCESS	read-only
		STATUS		current
		DESCRIPTION
			"Indicate the protection switch direction of this protection entry."
	    ::= { gslamAGProtectionGroupEntry 5 }

	gslamAGProtectionGroupRvrt		OBJECT-TYPE
		SYNTAX		FlagValue
		MAX-ACCESS	read-only
		STATUS		current
		DESCRIPTION
			"Indicate if it is protection revertable of this protection entry."
	    ::= { gslamAGProtectionGroupEntry 6 }

	gslamAGProtectionGroupLPID		OBJECT-TYPE
		SYNTAX		OCTET STRING(SIZE(0..64))
		MAX-ACCESS	read-write
		STATUS		current
		DESCRIPTION
			"The light path ID management application enters when creating 
				this protection group, return empty string if not available."
	    ::= { gslamAGProtectionGroupEntry 7 }

	gslamAGProtectionGroupSwitchCmd     OBJECT-TYPE
		SYNTAX      ProtectionSwitchCmdValue
		MAX-ACCESS  read-write
		STATUS      current
		DESCRIPTION
	    		"Indicate command issued to this GSLAM-AG protection group."
	    ::= { gslamAGProtectionGroupEntry 8 }

	gslamAGProtectionGroupActiveIndex		OBJECT-TYPE
		SYNTAX		Unsigned32
		MAX-ACCESS	read-only
		STATUS		current
		DESCRIPTION
			"The ifIndex value of the working entity (port, channel or opvcx) in the protection group."
	    ::= { gslamAGProtectionGroupEntry 9 }

     -- UV 5.0 CHANGE START 
     -- GSLAM-AG facility/path protection group objects.
	gslamAGREL50PrGrTable		OBJECT-TYPE
		SYNTAX		SEQUENCE OF GslamAGREL50PrGrEntry
		MAX-ACCESS	not-accessible
		STATUS		current
		DESCRIPTION
			"A table about the facility/path protection group of GSLAM-AG."
	    ::= { ipiGslamAGProtectionGroupObjs 2 }

	gslamAGREL50PrGrEntry OBJECT-TYPE
		SYNTAX  		GslamAGREL50PrGrEntry
		MAX-ACCESS	not-accessible
		STATUS  		current
		DESCRIPTION
			"A row in the GSLAM-AG protection group table."
		INDEX   { 	gslamAGREL50PrGrProtectedSIndex, 
			  		gslamAGREL50PrGrProtectedMIndex,
			  		gslamAGREL50PrGrProtectedPIndex,
                    gslamAGREL50PrGrProtectedCIndex,
			  		gslamAGREL50PrGrProtectedTIndex,
                    gslamAGREL50PrGrProtectingSIndex,
			  		gslamAGREL50PrGrProtectingMIndex,
                    gslamAGREL50PrGrProtectingPIndex,
			  		gslamAGREL50PrGrProtectingCIndex,
                    gslamAGREL50PrGrProtectingTIndex}
	    ::= { gslamAGREL50PrGrTable 1 }

	GslamAGREL50PrGrEntry ::= SEQUENCE {
		gslamAGREL50PrGrProtectedSIndex	     		Unsigned32,
		gslamAGREL50PrGrProtectedMIndex				Unsigned32,
		gslamAGREL50PrGrProtectedPIndex	        	Unsigned32,
		gslamAGREL50PrGrProtectedCIndex	        	Unsigned32,
		gslamAGREL50PrGrProtectedTIndex				Unsigned32,
		gslamAGREL50PrGrProtectingSIndex	       	Unsigned32,
		gslamAGREL50PrGrProtectingMIndex			Unsigned32,
		gslamAGREL50PrGrProtectingPIndex	       	Unsigned32,
		gslamAGREL50PrGrProtectingCIndex	       	Unsigned32,
		gslamAGREL50PrGrProtectingTIndex	       	Unsigned32,
		gslamAGREL50PrGrRowStatus		        	RowStatus,
		gslamAGREL50PrGrSwitchType	               	ProtectionSwitchTypeValue,
		gslamAGREL50PrGrSwitchDir		        	ProtectionSwitchDirValue,
		gslamAGREL50PrGrRvrt		               	FlagValue,
		gslamAGREL50PrGrLPID		               	OCTET STRING,
		gslamAGREL50PrGrSwitchCmd		        	ProtectionSwitchCmdValue,
		gslamAGREL50PrGrActiveSIndex	           	Unsigned32,
		gslamAGREL50PrGrActiveMIndex	           	Unsigned32,
		gslamAGREL50PrGrActivePIndex	           	Unsigned32,
		gslamAGREL50PrGrActiveCIndex	           	Unsigned32,
		gslamAGREL50PrGrActiveTIndex	           	Unsigned32
	}

	gslamAGREL50PrGrProtectedSIndex			OBJECT-TYPE
		SYNTAX		Unsigned32
		MAX-ACCESS	not-accessible
		STATUS		current
		DESCRIPTION
			"The index1 value of the shelf in the protected group."
	    ::= { gslamAGREL50PrGrEntry 1 }

	gslamAGREL50PrGrProtectedMIndex		OBJECT-TYPE
		SYNTAX		Unsigned32
		MAX-ACCESS	not-accessible
		STATUS		current
		DESCRIPTION
			"The index2 value of the module in the protected group."
	    ::= { gslamAGREL50PrGrEntry 2 }

	gslamAGREL50PrGrProtectedPIndex		OBJECT-TYPE
		SYNTAX		Unsigned32
		MAX-ACCESS	not-accessible
		STATUS		current
		DESCRIPTION
			"The index3 value of the port in the protected group."
	    ::= { gslamAGREL50PrGrEntry 3 }

	gslamAGREL50PrGrProtectedCIndex		OBJECT-TYPE
		SYNTAX		Unsigned32
		MAX-ACCESS	not-accessible
		STATUS		current
		DESCRIPTION
			"The index4 value of the chnl in the protected group."
	    ::= { gslamAGREL50PrGrEntry 4 }

	gslamAGREL50PrGrProtectedTIndex		OBJECT-TYPE
		SYNTAX		Unsigned32
		MAX-ACCESS	not-accessible
		STATUS		current
		DESCRIPTION
			"The index5 value of the ts in the protected group."
	    ::= { gslamAGREL50PrGrEntry 5 }

	gslamAGREL50PrGrProtectingSIndex		OBJECT-TYPE
		SYNTAX		Unsigned32
		MAX-ACCESS	not-accessible
		STATUS		current
		DESCRIPTION
			"The index1 value of the shelf in the protecting group."
	    ::= { gslamAGREL50PrGrEntry 6 }

	gslamAGREL50PrGrProtectingMIndex		OBJECT-TYPE
		SYNTAX		Unsigned32
		MAX-ACCESS	not-accessible
		STATUS		current
		DESCRIPTION
			"The index2 value of the module in the protecting group."
	    ::= { gslamAGREL50PrGrEntry 7 }

	gslamAGREL50PrGrProtectingPIndex		OBJECT-TYPE
		SYNTAX		Unsigned32
		MAX-ACCESS	not-accessible
		STATUS		current
		DESCRIPTION
			"The index3 value of the port in the protecting group."
	    ::= { gslamAGREL50PrGrEntry 8 }

	gslamAGREL50PrGrProtectingCIndex		OBJECT-TYPE
		SYNTAX		Unsigned32
		MAX-ACCESS	not-accessible
		STATUS		current
		DESCRIPTION
			"The index4 value of the chnl in the protecting group."
	    ::= { gslamAGREL50PrGrEntry 9 }

	gslamAGREL50PrGrProtectingTIndex		OBJECT-TYPE
		SYNTAX		Unsigned32
		MAX-ACCESS	not-accessible
		STATUS		current
		DESCRIPTION
			"The index5 value of the ts in the protecting group."
	    ::= { gslamAGREL50PrGrEntry 10 }

	gslamAGREL50PrGrRowStatus			OBJECT-TYPE
		SYNTAX		RowStatus
		MAX-ACCESS	read-create
		STATUS		current
		DESCRIPTION
			"Current status of this protection group entry."
	    ::= { gslamAGREL50PrGrEntry 11 }

	gslamAGREL50PrGrSwitchType			OBJECT-TYPE
		SYNTAX		ProtectionSwitchTypeValue
		MAX-ACCESS	read-only
		STATUS		current
		DESCRIPTION
			"Indicate the protection switch type of this protection entry."
	    ::= { gslamAGREL50PrGrEntry 12 }

	gslamAGREL50PrGrSwitchDir			OBJECT-TYPE
		SYNTAX		ProtectionSwitchDirValue
		MAX-ACCESS	read-only
		STATUS		current
		DESCRIPTION
			"Indicate the protection switch direction of this protection entry."
	    ::= { gslamAGREL50PrGrEntry 13 }

	gslamAGREL50PrGrRvrt				OBJECT-TYPE
		SYNTAX		FlagValue
		MAX-ACCESS	read-only
		STATUS		current
		DESCRIPTION
			"Indicate if it is protection revertable of this protection entry."
	    ::= { gslamAGREL50PrGrEntry 14 }

	gslamAGREL50PrGrLPID				OBJECT-TYPE
		SYNTAX		OCTET STRING(SIZE(0..64))
		MAX-ACCESS	read-write
		STATUS		current
		DESCRIPTION
			"The light path ID management application enters when creating this protection group,
                          return empty string if not available."
	    ::= { gslamAGREL50PrGrEntry 15 }

	gslamAGREL50PrGrSwitchCmd     			OBJECT-TYPE
		SYNTAX      ProtectionSwitchCmdValue
		MAX-ACCESS  read-write
		STATUS      current
		DESCRIPTION
	    		"Indicate command issued to this GSLAM-AG protection group."
	    ::= { gslamAGREL50PrGrEntry 16 }

	gslamAGREL50PrGrActiveSIndex			OBJECT-TYPE
		SYNTAX		Unsigned32
		MAX-ACCESS	read-only
		STATUS		current
		DESCRIPTION
			"The ifIndex value of the working entity (port, channel or opvcx) in the protection group."
	    ::= { gslamAGREL50PrGrEntry 17 }
	
	gslamAGREL50PrGrActiveMIndex			OBJECT-TYPE
		SYNTAX		Unsigned32
		MAX-ACCESS	read-only
		STATUS		current
		DESCRIPTION
			"The ifIndex value of the working entity (port, channel or opvcx) in the protection group."
	    ::= { gslamAGREL50PrGrEntry 18 }

	gslamAGREL50PrGrActivePIndex			OBJECT-TYPE
		SYNTAX		Unsigned32
		MAX-ACCESS	read-only
		STATUS		current
		DESCRIPTION
			"The ifIndex value of the working entity (port, channel or opvcx) in the protection group."
	    ::= { gslamAGREL50PrGrEntry 19 }

	gslamAGREL50PrGrActiveCIndex			OBJECT-TYPE
		SYNTAX		Unsigned32
		MAX-ACCESS	read-only
		STATUS		current
		DESCRIPTION
			"The ifIndex value of the working entity (port, channel or opvcx) in the protection group."
	    ::= { gslamAGREL50PrGrEntry 20 }

	gslamAGREL50PrGrActiveTIndex			OBJECT-TYPE
		SYNTAX		Unsigned32
		MAX-ACCESS	read-only
		STATUS		current
		DESCRIPTION
			"The ifIndex value of the working entity (port, channel or opvcx) in the protection group."
	    ::= { gslamAGREL50PrGrEntry 21 }

    -- UV 5.0 CHANGE END

	-- GSLAM-AG TID address map objects.
	gslamAGTAdrMapTable		OBJECT-TYPE
		SYNTAX		SEQUENCE OF GslamAGTAdrMapEntry
		MAX-ACCESS	not-accessible
		STATUS		current
		DESCRIPTION
			"A table about the TID address map of GSLAM-AG."
	    ::= { ipiGslamAGTAdrMapObjs 1 }

	gslamAGTAdrMapEntry OBJECT-TYPE
		SYNTAX  		GslamAGTAdrMapEntry
		MAX-ACCESS		not-accessible
		STATUS  		current
		DESCRIPTION
			"A row in the GSLAM-AG Tid address map table."
		INDEX   { gslamAGTAdrMapName }
	    ::= { gslamAGTAdrMapTable 1 }

	GslamAGTAdrMapEntry ::= SEQUENCE {
		gslamAGTAdrMapName		OCTET STRING,
		gslamAGTAdrMapIP			IpAddress,
		gslamAGTAdrMapPortNumber	Unsigned32
	}

	gslamAGTAdrMapName		OBJECT-TYPE
		SYNTAX		OCTET STRING(SIZE(1..20))
		MAX-ACCESS	read-only
		STATUS		current
		DESCRIPTION
			"The name of this map entry, used as index."
	    ::= { gslamAGTAdrMapEntry 1 }

	gslamAGTAdrMapIP		OBJECT-TYPE
		SYNTAX		IpAddress
		MAX-ACCESS	read-only
		STATUS		current
		DESCRIPTION
			"The IP address of this map entry."
	    ::= { gslamAGTAdrMapEntry 2 }

	gslamAGTAdrMapPortNumber		OBJECT-TYPE
		SYNTAX		Unsigned32
		MAX-ACCESS	read-only
		STATUS		current
		DESCRIPTION
			"The associated port number of this map entry."
	    ::= { gslamAGTAdrMapEntry 3 }

	-- Control connection table
	gslamAGControlConnectionTable    OBJECT-TYPE
		SYNTAX          SEQUENCE OF GslamAGControlConnectionEntry
		MAX-ACCESS      not-accessible
		STATUS          current
		DESCRIPTION
			"A table of status of control connections to the neighboring nodes."
		::= { ipiGslamAGControlConnectionObjs 1 }

	gslamAGControlConnectionEntry    OBJECT-TYPE
		SYNTAX          GslamAGControlConnectionEntry
		MAX-ACCESS      not-accessible
		STATUS          current
		DESCRIPTION
			"A row in the CN4200's control connection table."
		INDEX  { gslamAGControlConnectionEthIndex }
		::= { gslamAGControlConnectionTable 1 }


	GslamAGControlConnectionEntry ::= SEQUENCE {
		gslamAGControlConnectionEthIndex         Unsigned32,
		gslamAGControlConnectionLocalIP          IpAddress,
		gslamAGControlConnectionRemoteNodeIP     IpAddress,
		gslamAGControlConnectionRemoteIP         IpAddress,
		gslamAGControlConnectionRemoteNodeType	RemoteNodeTypeValue,
		gslamAGControlConnectionLocalNodeTID	OCTET STRING,
		gslamAGControlConnectionRemoteNodeTID	OCTET STRING,
		gslamAGControlConnectionStatus		INTEGER,
		gslamAGControlConnectionType		INTEGER,
		gslamAGControlConnectionRemoteEthIndex         Unsigned32
	}

	gslamAGControlConnectionEthIndex                  OBJECT-TYPE
		SYNTAX          Unsigned32
		MAX-ACCESS      read-only
		STATUS          current
		DESCRIPTION
			"Indicates the index of the management ethernet interface."
		::= { gslamAGControlConnectionEntry 1 }

	gslamAGControlConnectionLocalIP                  OBJECT-TYPE
		SYNTAX          IpAddress
		MAX-ACCESS      read-only
		STATUS          current
		DESCRIPTION
			"Indicates the IP address of the local end of this control connection."
		::= { gslamAGControlConnectionEntry 2 }

	gslamAGControlConnectionRemoteNodeIP         OBJECT-TYPE
		SYNTAX          IpAddress
		MAX-ACCESS      read-only
		STATUS          current
		DESCRIPTION
                        "Indicates the IP address of the remote node of this control connection."
		::= { gslamAGControlConnectionEntry 3 }

	gslamAGControlConnectionRemoteIP         OBJECT-TYPE
		SYNTAX          IpAddress
		MAX-ACCESS      read-only
		STATUS          current
		DESCRIPTION
                        "Indicates the IP address of the remote end of this control connection."
		::= { gslamAGControlConnectionEntry 4 }

   	gslamAGControlConnectionRemoteNodeType		OBJECT-TYPE
        	SYNTAX	RemoteNodeTypeValue
        	MAX-ACCESS      read-only
		STATUS          current
		DESCRIPTION
                        "Indicates the equiptment type of the remote end of this control connection."
		::= { gslamAGControlConnectionEntry 5 }

	gslamAGControlConnectionLocalNodeTID		OBJECT-TYPE
		SYNTAX		OCTET STRING(SIZE(1..20))
		MAX-ACCESS	read-only
		STATUS		current
		DESCRIPTION
			"Indicates the TID of the local end of this control connection."
	::= { gslamAGControlConnectionEntry 6 }

	gslamAGControlConnectionRemoteNodeTID		OBJECT-TYPE
		SYNTAX		OCTET STRING(SIZE(1..20))
		MAX-ACCESS	read-only
		STATUS		current
		DESCRIPTION
			"Indicates the TID of the remote end of this control connection."
	::= { gslamAGControlConnectionEntry 7 }

	gslamAGControlConnectionStatus	OBJECT-TYPE
		SYNTAX		INTEGER {
						unknown(1),
						ndp-enabled(2),
						admin-enabled(3)
		}
		MAX-ACCESS	read-only
		STATUS		current
		DESCRIPTION
			"Used to indicate if the connection is ndp or admin enabled."
	::= { gslamAGControlConnectionEntry 8 }

	gslamAGControlConnectionType	OBJECT-TYPE
		SYNTAX		INTEGER {
						unknown(1),
						pt2pt(2),
						backplane(3)
		}
		MAX-ACCESS	read-only
		STATUS		current
		DESCRIPTION
			"Used to indicate if the connection is point-to-point or backplane."
	::= { gslamAGControlConnectionEntry 9 }

	gslamAGControlConnectionRemoteEthIndex                  OBJECT-TYPE
		SYNTAX          Unsigned32
		MAX-ACCESS      read-only
		STATUS          current
		DESCRIPTION
			"Indicates the remote index of the management ethernet interface."
		::= { gslamAGControlConnectionEntry 10 }

   -- GSLAM-AG PE association objects.
	gslamAGPEAssociationTable		OBJECT-TYPE
		SYNTAX		SEQUENCE OF GslamAGPEAssociationEntry
		MAX-ACCESS	not-accessible
		STATUS		current
		DESCRIPTION
			"A table about the all the PE association of GSLAM-AG."
	    ::= { ipiGslamAGPEAssociationObjs 1 }

	gslamAGPEAssociationEntry OBJECT-TYPE
		SYNTAX  		GslamAGPEAssociationEntry
		MAX-ACCESS	not-accessible
		STATUS  		current
		DESCRIPTION
			"A row in the GSLAM-AG PE association table."
		INDEX   { gslamAGPEAssociationFromIfIndex, gslamAGPEAssociationToIfIndex }
	    ::= { gslamAGPEAssociationTable 1 }

	GslamAGPEAssociationEntry ::= SEQUENCE {
		gslamAGPEAssociationFromIfIndex	Unsigned32,
		gslamAGPEAssociationToIfIndex	Unsigned32,
		gslamAGPEAssociationFromPEType	EquipmentTypeValue,
		gslamAGPEAssociationToPEType	EquipmentTypeValue,
		gslamAGPEAssociationDirection	ConnModeValue,
		gslamAGPEAssociationCktID		OCTET STRING
	}

	gslamAGPEAssociationFromIfIndex		OBJECT-TYPE
		SYNTAX		Unsigned32
		MAX-ACCESS	not-accessible
		STATUS		current
		DESCRIPTION
			"The first index of GSLAM-AG PE association table. It indicates
			the 'from' part of ifIndex in the PE association. Each ifIndex is a 32-bit
			unsigned integer. From left (most significant) to right, we allocate 4
			bits for unit(shelf) id, 4 bits for IO module id, 4 bits for interface(port)
			id, 4 bits for channel id, and the rest (rightmost) 16 bits for OPVC group."
	    ::= { gslamAGPEAssociationEntry 1 }

	gslamAGPEAssociationToIfIndex		OBJECT-TYPE
		SYNTAX		Unsigned32
		MAX-ACCESS	not-accessible
		STATUS		current
		DESCRIPTION
			"The second index of GSLAM-AG PE association table. It indicates
			the 'to' part of ifIndex in the PE association. Each ifIndex is a 32-bit
			unsigned integer. From left (most significant) to right, we allocate 4
			bits for unit(shelf) id, 4 bits for IO module id, 4 bits for interface(port)
			id, 4 bits for channel id, and the rest (rightmost) 16 bits for OPVC group."
	    ::= { gslamAGPEAssociationEntry 2 }

	gslamAGPEAssociationFromPEType	OBJECT-TYPE
		SYNTAX		EquipmentTypeValue
		MAX-ACCESS	read-only
		STATUS		current
		DESCRIPTION
			"The PE type of the 'from' part in PE association"
	    ::= { gslamAGPEAssociationEntry 3}

	gslamAGPEAssociationToPEType	OBJECT-TYPE
		SYNTAX		EquipmentTypeValue
		MAX-ACCESS	read-only
		STATUS		current
		DESCRIPTION
			"The PE type of the 'to' part in PE association"
	    ::= { gslamAGPEAssociationEntry 4}

	gslamAGPEAssociationDirection	OBJECT-TYPE
		SYNTAX	ConnModeValue
 	 	MAX-ACCESS  read-only
 	 	STATUS      current
 	 	DESCRIPTION
			"Indicates the direction of this PE association. For unidirection, traffic goes
				from 'from' to 'to'. Default value is bidirection"
 	 	::= { gslamAGPEAssociationEntry 5}

	gslamAGPEAssociationCktID		OBJECT-TYPE
		SYNTAX		OCTET STRING(SIZE(0..64))
		MAX-ACCESS	read-only
		STATUS		current
		DESCRIPTION
			"The connection ID management application using for creating this connection, 
			Return empty string if not available."
	    ::= { gslamAGPEAssociationEntry 6}

	-- UV 5.0 change start
	gslamAGREL50PEAssocTable		OBJECT-TYPE
		SYNTAX		SEQUENCE OF GslamAGREL50PEAssocEntry
		MAX-ACCESS	not-accessible
		STATUS		current
		DESCRIPTION
			"A table about the all the PE association of GSLAM-AG."
	    ::= { ipiGslamAGPEAssociationObjs 2 }

	gslamAGREL50PEAssocEntry OBJECT-TYPE
		SYNTAX  		GslamAGREL50PEAssocEntry
		MAX-ACCESS	not-accessible
		STATUS  		current
		DESCRIPTION
			"A row in the GSLAM-AG PE association table."
		INDEX   { gslamAGREL50PEAssocFromSIndex, gslamAGREL50PEAssocFromMIndex,
			      gslamAGREL50PEAssocFromPIndex, gslamAGREL50PEAssocFromCIndex,
			      gslamAGREL50PEAssocFromTIndex, gslamAGREL50PEAssocToSIndex,
			      gslamAGREL50PEAssocToMIndex,   gslamAGREL50PEAssocToPIndex,
			      gslamAGREL50PEAssocToCIndex,   gslamAGREL50PEAssocToTIndex}
	    ::= { gslamAGREL50PEAssocTable 1 }

	GslamAGREL50PEAssocEntry::= SEQUENCE {
		gslamAGREL50PEAssocFromSIndex	Unsigned32,
		gslamAGREL50PEAssocFromMIndex	Unsigned32,
		gslamAGREL50PEAssocFromPIndex	Unsigned32,
		gslamAGREL50PEAssocFromCIndex	Unsigned32,
		gslamAGREL50PEAssocFromTIndex	Unsigned32,
		gslamAGREL50PEAssocToSIndex		Unsigned32,
		gslamAGREL50PEAssocToMIndex		Unsigned32,
		gslamAGREL50PEAssocToPIndex		Unsigned32,
		gslamAGREL50PEAssocToCIndex		Unsigned32,
		gslamAGREL50PEAssocToTIndex		Unsigned32,	
		gslamAGREL50PEAssocFromPEType	EquipmentTypeValue,
		gslamAGREL50PEAssocToPEType		EquipmentTypeValue,
		gslamAGREL50PEAssocDirection	ConnModeValue,
		gslamAGREL50PEAssocCktID		OCTET STRING
	}
	
	gslamAGREL50PEAssocFromSIndex		OBJECT-TYPE
		SYNTAX		Unsigned32
		MAX-ACCESS	not-accessible
		STATUS		current
		DESCRIPTION
			"The Shelf index of GSLAM-AG PE association table."
	    ::= { gslamAGREL50PEAssocEntry 1 }

	gslamAGREL50PEAssocFromMIndex		OBJECT-TYPE
		SYNTAX		Unsigned32
		MAX-ACCESS	not-accessible
		STATUS		current
		DESCRIPTION
			"The Shelf index of GSLAM-AG PE association table."
	    ::= { gslamAGREL50PEAssocEntry 2 }
	
	gslamAGREL50PEAssocFromPIndex		OBJECT-TYPE
		SYNTAX		Unsigned32
		MAX-ACCESS	not-accessible
		STATUS		current
		DESCRIPTION
			"The Shelf index of GSLAM-AG PE association table."
	    ::= { gslamAGREL50PEAssocEntry 3 }

	gslamAGREL50PEAssocFromCIndex		OBJECT-TYPE
		SYNTAX		Unsigned32
		MAX-ACCESS	not-accessible
		STATUS		current
		DESCRIPTION
			"The Shelf index of GSLAM-AG PE association table."
	    ::= { gslamAGREL50PEAssocEntry 4 }

	gslamAGREL50PEAssocFromTIndex		OBJECT-TYPE
		SYNTAX		Unsigned32
		MAX-ACCESS	not-accessible
		STATUS		current
		DESCRIPTION
			"The Shelf index of GSLAM-AG PE association table."
	    ::= { gslamAGREL50PEAssocEntry 5 }

	gslamAGREL50PEAssocToSIndex		OBJECT-TYPE
		SYNTAX		Unsigned32
		MAX-ACCESS	not-accessible
		STATUS		current
		DESCRIPTION
			"The shelf index of GSLAM-AG PE association table."
	    ::= { gslamAGREL50PEAssocEntry 6 }

	gslamAGREL50PEAssocToMIndex		OBJECT-TYPE
		SYNTAX		Unsigned32
		MAX-ACCESS	not-accessible
		STATUS		current
		DESCRIPTION
			"The shelf index of GSLAM-AG PE association table."
	    ::= { gslamAGREL50PEAssocEntry 7 }
	
	gslamAGREL50PEAssocToPIndex		OBJECT-TYPE
		SYNTAX		Unsigned32
		MAX-ACCESS	not-accessible
		STATUS		current
		DESCRIPTION
			"The shelf index of GSLAM-AG PE association table."
	    ::= { gslamAGREL50PEAssocEntry 8 }

	gslamAGREL50PEAssocToCIndex		OBJECT-TYPE
		SYNTAX		Unsigned32
		MAX-ACCESS	not-accessible
		STATUS		current
		DESCRIPTION
			"The shelf index of GSLAM-AG PE association table."
	    ::= { gslamAGREL50PEAssocEntry 9 }

	gslamAGREL50PEAssocToTIndex		OBJECT-TYPE
		SYNTAX		Unsigned32
		MAX-ACCESS	not-accessible
		STATUS		current
		DESCRIPTION
			"The shelf index of GSLAM-AG PE association table."
	    ::= { gslamAGREL50PEAssocEntry 10 }

	gslamAGREL50PEAssocFromPEType	OBJECT-TYPE
		SYNTAX		EquipmentTypeValue
		MAX-ACCESS	read-only
		STATUS		current
		DESCRIPTION
			"The PE type of the 'from' part in PE association"
	    ::= { gslamAGREL50PEAssocEntry 11}

	gslamAGREL50PEAssocToPEType	OBJECT-TYPE
		SYNTAX		EquipmentTypeValue
		MAX-ACCESS	read-only
		STATUS		current
		DESCRIPTION
			"The PE type of the 'to' part in PE association"
	    ::= { gslamAGREL50PEAssocEntry 12}

	gslamAGREL50PEAssocDirection	OBJECT-TYPE
		SYNTAX	ConnModeValue
 	 	MAX-ACCESS  read-only
 	 	STATUS      current
 	 	DESCRIPTION
			"Indicates the direction of this PE association. For unidirection, traffic goes
				from 'from' to 'to'. Default value is bidirection"
 	 	::= { gslamAGREL50PEAssocEntry 13}

	gslamAGREL50PEAssocCktID		OBJECT-TYPE
		SYNTAX		OCTET STRING(SIZE(0..64))
		MAX-ACCESS	read-only
		STATUS		current
		DESCRIPTION
			"The connection ID management application using for creating this connection, 
			Return empty string if not available."
	    ::= { gslamAGREL50PEAssocEntry 14}

	-- UV 5.0 STOP

	-- CondAll objs
	gslamAGCondAllTable		OBJECT-TYPE
		SYNTAX		SEQUENCE OF GslamAGCondAllEntry
		MAX-ACCESS	not-accessible
		STATUS		current
		DESCRIPTION
			"A table about the current status of all standing conditions in the GSLAM-AG."
	    ::= { ipiGslamAGCondAllObjs 1 }

	gslamAGCondAllEntry OBJECT-TYPE
		SYNTAX  		GslamAGCondAllEntry
		MAX-ACCESS		not-accessible
		STATUS  		current
		DESCRIPTION
			"A row in the GSLAM-AG standing conditions table."
		INDEX { gslamAGCondAllCondType, gslamAGCondAllSeqNum }
	    ::= { gslamAGCondAllTable 1 }

	GslamAGCondAllEntry ::= SEQUENCE {
		gslamAGCondAllCondType	ConditionType,
		gslamAGCondAllSeqNum	Unsigned32,
		gslamAGCondAllEqptAddr	OBJECT IDENTIFIER,
		gslamAGCondAllEqptType	EquipmentTypeValue,
		gslamAGCondAllCondCode	INTEGER,
		gslamAGCondAllSrvEff	INTEGER,
		gslamAGCondAllTimeStamp	DateAndTime,
		gslamAGCondAllDirn		INTEGER,
		gslamAGCondAllCondDescr	OCTET STRING
	}

	gslamAGCondAllCondType	OBJECT-TYPE
		SYNTAX		ConditionType
		MAX-ACCESS	read-only
		STATUS		current
		DESCRIPTION
			"Used to indicate the condition type of the event."
	    ::= { gslamAGCondAllEntry 1 }

	gslamAGCondAllSeqNum		OBJECT-TYPE
		SYNTAX		Unsigned32
		MAX-ACCESS	not-accessible
		STATUS		current
		DESCRIPTION
			"The sequence number of the entry in this condition table."
	    ::= { gslamAGCondAllEntry 2 }

	gslamAGCondAllEqptAddr	OBJECT-TYPE
		SYNTAX		OBJECT IDENTIFIER
		MAX-ACCESS	read-only
		STATUS		current
		DESCRIPTION
			"Used to indicate the OID of the physical entity involved in this event."
	    ::= { gslamAGCondAllEntry 3 }

	gslamAGCondAllEqptType	OBJECT-TYPE
		SYNTAX		EquipmentTypeValue
		MAX-ACCESS	read-only
		STATUS		current
		DESCRIPTION
			"Used to indicate the type of the physical entity involved in this event."
	    ::= { gslamAGCondAllEntry 4 }

	gslamAGCondAllCondCode	OBJECT-TYPE
		SYNTAX INTEGER {
			unknown(1),
			cleared(2),
			critical(3),
			major(4),
			minor(5),
			not-alarmed(6),
			not-reported(7)
		}
		MAX-ACCESS	read-only
		STATUS		current
		DESCRIPTION
			"Used to indicate the severity of the alarm (if applicable) for the event."
	    ::= { gslamAGCondAllEntry 5 }

	gslamAGCondAllSrvEff	OBJECT-TYPE
		SYNTAX INTEGER {
			unknown(1),
			service-affected(2),
			not-service-affected(3),
			not-applicable(4)
		}
		MAX-ACCESS	read-only
		STATUS		current
		DESCRIPTION
			"Used to indicate the service effect of this event."
	    ::= { gslamAGCondAllEntry 6 }

	gslamAGCondAllTimeStamp	OBJECT-TYPE
		SYNTAX		DateAndTime
		MAX-ACCESS	read-only
		STATUS		current
		DESCRIPTION
			"Indicates the timestamp when this event occured."
	    ::= { gslamAGCondAllEntry 7 }

	gslamAGCondAllDirn	OBJECT-TYPE
		SYNTAX INTEGER {
			unknown(1),
			rcv(2),
			trmt(3),
			rcv-trmt(4),
			not-present(5)
		}
		MAX-ACCESS	read-only
		STATUS		current
		DESCRIPTION
			"Used to indicate the direction of the event."
	    ::= { gslamAGCondAllEntry 8 }

	gslamAGCondAllCondDescr	OBJECT-TYPE
		SYNTAX		OCTET STRING(SIZE(1..64))
		MAX-ACCESS	read-only
		STATUS		current
		DESCRIPTION
			"Condition description of the event."
	    ::= { gslamAGCondAllEntry 9 }

	-- Optical management Objs

	gslamAGOpticalDegreeTable	OBJECT-TYPE
		SYNTAX		SEQUENCE OF GslamAGOpticalDegreeEntry
		MAX-ACCESS	not-accessible
		STATUS		current
		DESCRIPTION
			"A table about the current status of
			 all optical degrees in the GSLAM-AG."
	    ::= { ipiGslamAGOpticalDegreeMgmtObjs 1 }

	gslamAGOpticalDegreeEntry OBJECT-TYPE
		SYNTAX  		GslamAGOpticalDegreeEntry
		MAX-ACCESS		not-accessible
		STATUS  		current
		DESCRIPTION
			"A row in the GSLAM-AG Optical Degree table."
		INDEX { gslamAGOpticalDegreeId }
	    ::= { gslamAGOpticalDegreeTable 1 }

	GslamAGOpticalDegreeEntry ::= SEQUENCE {
		gslamAGOpticalDegreeId			Unsigned32,
		gslamAGOpticalDegreeRowStatus		RowStatus,
		gslamAGOpticalDegreeName		OCTET STRING,
		gslamAGOpticalDegreeOSC			FlagValue,
		gslamAGOpticalDegreeAmplificationConfig		AmplificationConfigModeValue,
        gslamAGOpticalDegreeNominalPerChnlOPPwr     OCTET STRING,
        gslamAGOpticalDegreeNtwkFibType2            INTEGER,
        gslamAGOpticalDegreeTotalDispersion         INTEGER,
        gslamAGOpticalDegreeNtwkFibLen              INTEGER,
        gslamAGOpticalDegreeAPSDControl             INTEGER,
        gslamAGOpticalDegreeAPSDStatus              INTEGER 
	}

	gslamAGOpticalDegreeId	OBJECT-TYPE
		SYNTAX		Unsigned32
		MAX-ACCESS	not-accessible
		STATUS		current
		DESCRIPTION
			"Degree interface identifier for an optical interface."
	    ::= { gslamAGOpticalDegreeEntry 1 }

	gslamAGOpticalDegreeRowStatus		OBJECT-TYPE
		SYNTAX		RowStatus
		MAX-ACCESS	read-create
		STATUS		current
		DESCRIPTION
			"Current status of this Optical Degree entry."
    	::= { gslamAGOpticalDegreeEntry 2 }

	gslamAGOpticalDegreeName	OBJECT-TYPE
		SYNTAX		OCTET STRING(SIZE(1..63))
		MAX-ACCESS	read-write
		STATUS		current
		DESCRIPTION
			"Degree interface name for an optical interface."
	    ::= { gslamAGOpticalDegreeEntry 3 }

	gslamAGOpticalDegreeOSC	OBJECT-TYPE
		SYNTAX		FlagValue
		MAX-ACCESS	read-write
		STATUS		current
		DESCRIPTION
			"Indicate if optical interface provides the
			 Optical Supervisory Channel "
	    ::= { gslamAGOpticalDegreeEntry 4 }

	gslamAGOpticalDegreeAmplificationConfig	OBJECT-TYPE
		SYNTAX		AmplificationConfigModeValue
		MAX-ACCESS	read-write
		STATUS		current
		DESCRIPTION
			"Defines the optical amplifier configuration for the interface "
	    ::= { gslamAGOpticalDegreeEntry 5 }

    gslamAGOpticalDegreeNominalPerChnlOPPwr  OBJECT-TYPE
        SYNTAX      OCTET STRING(SIZE(1..63))
        MAX-ACCESS  read-write
        STATUS      current
        DESCRIPTION
            " The nominal per channel output power for the degree.
                 -17.0 to +13.0 (dBm). Default Value = 1"
        ::= { gslamAGOpticalDegreeEntry 6 }

    gslamAGOpticalDegreeNtwkFibType2 OBJECT-TYPE
        SYNTAX      INTEGER {
            unknown(1),
            unprovisioned(2),
            g652(3),
            g653(4),
            g655EL(5),
            g655LS(6),
            g655TW(7)
        }
        MAX-ACCESS  read-write
        STATUS      current
        DESCRIPTION
            "This is the fiber type. Default is unprovisioned"
        ::= { gslamAGOpticalDegreeEntry 7 }

    gslamAGOpticalDegreeTotalDispersion OBJECT-TYPE
        SYNTAX      INTEGER (-1500..3000)
        MAX-ACCESS  read-write
        STATUS      current
        DESCRIPTION
            " The optical total dispersion.
             -1500 to 3000 (ps/nm). Default Value = 1. No Default"
        ::= { gslamAGOpticalDegreeEntry 8 }

    gslamAGOpticalDegreeNtwkFibLen OBJECT-TYPE
        SYNTAX      INTEGER (0..200)
        MAX-ACCESS  read-write
        STATUS      current
        DESCRIPTION
            "This is the fiber length. Default is 0"
        ::= { gslamAGOpticalDegreeEntry 9 }

     gslamAGOpticalDegreeAPSDControl OBJECT-TYPE
        SYNTAX      INTEGER {
            unknown (1),
            enabled (2),
            disabled (3),
            manrestart(4)
        }
        MAX-ACCESS  read-write
        STATUS      current
        DESCRIPTION
            "This is APSD control. Default is enabled"
        ::= { gslamAGOpticalDegreeEntry 10 }

    gslamAGOpticalDegreeAPSDStatus OBJECT-TYPE
        SYNTAX      INTEGER {
            unknown (1),
            shutdown (2),
            shutdown-fail (3),
            normal(4)
        }
        MAX-ACCESS  read-only
        STATUS      current
        DESCRIPTION
            "This is APSD status" 
        ::= { gslamAGOpticalDegreeEntry 11 }

	-- ROADM 5.0 START
	gslamAGREL50OpticalROADMDegreeTable	OBJECT-TYPE
		SYNTAX		SEQUENCE OF GslamAGREL50OpticalROADMDegreeEntry
		MAX-ACCESS	not-accessible
		STATUS		current
		DESCRIPTION
			"A table about the current status of
			 all optical degrees in the GSLAM-AG."
	::= { ipiGslamAGOpticalDegreeMgmtObjs 2 }

	gslamAGREL50OpticalROADMDegreeEntry OBJECT-TYPE
		SYNTAX  		GslamAGREL50OpticalROADMDegreeEntry
		MAX-ACCESS		not-accessible
		STATUS  		current
		DESCRIPTION
			"A row in the GSLAM-AG Optical Degree table."
		INDEX { gslamAGREL50OpticalROADMDegreeId }
	    ::= { gslamAGREL50OpticalROADMDegreeTable 1 }

	GslamAGREL50OpticalROADMDegreeEntry ::= SEQUENCE {
		gslamAGREL50OpticalROADMDegreeId			Unsigned32,
		gslamAGREL50OpticalROADMDegreeRowStatus		RowStatus,
		gslamAGREL50OpticalROADMDegreeName		OCTET STRING,
		gslamAGREL50OpticalROADMDegreeOSC			FlagValue,
		gslamAGREL50OpticalROADMDegreeAmplificationConfig		AmplificationConfigModeValue,
		gslamAGREL50OpticalROADMNominalPerChnlOPPwr  OCTET STRING,
		gslamAGREL50OpticalROADMNtwkFibType   INTEGER,
		gslamAGREL50OpticalROADMTotalDispersion    INTEGER,
        gslamAGREL50OpticalROADMNtwkFibType2            INTEGER,
        gslamAGREL50OpticalROADMNtwkFibLen              INTEGER,
        gslamAGREL50OpticalROADMAPSDControl             INTEGER,
        gslamAGREL50OpticalROADMAPSDStatus              INTEGER 
	}

	gslamAGREL50OpticalROADMDegreeId	OBJECT-TYPE
		SYNTAX		Unsigned32
		MAX-ACCESS	not-accessible
		STATUS		current
		DESCRIPTION
			"Degree interface identifier for an optical interface."
	    ::= { gslamAGREL50OpticalROADMDegreeEntry 1 }

	gslamAGREL50OpticalROADMDegreeRowStatus		OBJECT-TYPE
		SYNTAX		RowStatus
		MAX-ACCESS	read-create
		STATUS		current
		DESCRIPTION
			"Current status of this Optical Degree entry."
    	::= { gslamAGREL50OpticalROADMDegreeEntry 2 }

	gslamAGREL50OpticalROADMDegreeName	OBJECT-TYPE
		SYNTAX		OCTET STRING(SIZE(1..63))
		MAX-ACCESS	read-write
		STATUS		current
		DESCRIPTION
			"Degree interface name for an optical interface."
	    ::= { gslamAGREL50OpticalROADMDegreeEntry 3 }

	gslamAGREL50OpticalROADMDegreeOSC	OBJECT-TYPE
		SYNTAX		FlagValue
		MAX-ACCESS	read-write
		STATUS		current
		DESCRIPTION
			"Indicate if optical interface provides the
			 Optical Supervisory Channel "
	    ::= { gslamAGREL50OpticalROADMDegreeEntry 4 }

	gslamAGREL50OpticalROADMDegreeAmplificationConfig	OBJECT-TYPE
		SYNTAX		AmplificationConfigModeValue
		MAX-ACCESS	read-write
		STATUS		current
		DESCRIPTION
			"Defines the optical amplifier configuration for the interface "
	    ::= { gslamAGREL50OpticalROADMDegreeEntry 5 }

	gslamAGREL50OpticalROADMNominalPerChnlOPPwr  OBJECT-TYPE
       	SYNTAX      OCTET STRING(SIZE(1..63))
       	MAX-ACCESS  read-write
       	STATUS      current
       	DESCRIPTION
           	" The nominal per channel output power for the degree.
                 -17.0 to +13.0 (dBm). Default Value = 1"
       	::= { gslamAGREL50OpticalROADMDegreeEntry 6 }

	gslamAGREL50OpticalROADMNtwkFibType	OBJECT-TYPE
       	SYNTAX      INTEGER {
       		unknown(1),
       		g652(2),
       		g653(3),
       		g655(4)
    	}        	
		MAX-ACCESS  read-write
       	STATUS     deprecated 
       	DESCRIPTION
    		"This is the fiber type. Default is G652"
       	::= { gslamAGREL50OpticalROADMDegreeEntry 7 }

	gslamAGREL50OpticalROADMTotalDispersion OBJECT-TYPE
       	SYNTAX      INTEGER (-1500..3000)
       	MAX-ACCESS  read-write
       	STATUS      current
       	DESCRIPTION
           	" The optical total dispersion.
			 -1500 to 3000 (ps/nm). Default Value = 1. No Default"
       	::= { gslamAGREL50OpticalROADMDegreeEntry 8 }

    gslamAGREL50OpticalROADMNtwkFibType2 OBJECT-TYPE
        SYNTAX      INTEGER {
            unknown(1),
            unprovisioned(2),
            g652(3),
            g653(4),
            g655EL(5),
            g655LS(6),
            g655TW(7)
        }
        MAX-ACCESS  read-write
        STATUS      current
        DESCRIPTION
            "This is the fiber type. Default is unprovisioned"
        ::= { gslamAGREL50OpticalROADMDegreeEntry 9 }

    gslamAGREL50OpticalROADMNtwkFibLen OBJECT-TYPE
        SYNTAX      INTEGER (0..200)
        MAX-ACCESS  read-write
        STATUS      current
        DESCRIPTION
            "This is the fiber length. Default is 0"
        ::= { gslamAGREL50OpticalROADMDegreeEntry 10 }

     gslamAGREL50OpticalROADMAPSDControl OBJECT-TYPE
        SYNTAX      INTEGER {
            unknown (1),
            enabled (2),
            disabled (3),
            manrestart(4)
        }
        MAX-ACCESS  read-write
        STATUS      current
        DESCRIPTION
            "This is APSD control. Default is enabled"
        ::= { gslamAGREL50OpticalROADMDegreeEntry 11 }

    gslamAGREL50OpticalROADMAPSDStatus OBJECT-TYPE
        SYNTAX      INTEGER {
            unknown (1),
            shutdown (2),
            shutdown-fail (3),
            normal(4)
        }
        MAX-ACCESS  read-only
        STATUS      current
        DESCRIPTION
            "This is APSD status"
        ::= { gslamAGREL50OpticalROADMDegreeEntry 12 }

	-- ROADM 5.0 END

	-- *********** R5.0 DEGREE BY NAME *******************
	gslamAGREL50DegreeByNameTable	OBJECT-TYPE
		SYNTAX		SEQUENCE OF GslamAGREL50DegreeByNameEntry
		MAX-ACCESS	not-accessible
		STATUS		current
		DESCRIPTION
			"A table about the current status of
			 all optical degrees in the GSLAM-AG."
	    ::= { ipiGslamAGOpticalDegreeMgmtObjs 3 }

	gslamAGREL50DegreeByNameEntry OBJECT-TYPE
		SYNTAX  		GslamAGREL50DegreeByNameEntry
		MAX-ACCESS		not-accessible
		STATUS  		current
		DESCRIPTION
			"A row in the GSLAM-AG Optical Degree table."
		INDEX { gslamAGREL50DegreeByNameString }
	    ::= { gslamAGREL50DegreeByNameTable 1 }

	GslamAGREL50DegreeByNameEntry ::= SEQUENCE {
		gslamAGREL50DegreeByNameString          	OCTET STRING,
		gslamAGREL50DegreeByNameDegreeId			Unsigned32,
		gslamAGREL50DegreeByNameOSC					FlagValue,
		gslamAGREL50DegreeByNameAmplificationConfig		AmplificationConfigModeValue,
		gslamAGREL50DegreeByNameNominalPerChnlOPPwr  			OCTET STRING,
		gslamAGREL50DegreeByNameNtwkFibType   					INTEGER,
		gslamAGREL50DegreeByNameTotalDispersion    				INTEGER,
        gslamAGREL50DegreeByNameNtwkFibType2                    INTEGER,
        gslamAGREL50DegreeByNameNtwkFibLen                      INTEGER,
        gslamAGREL50DegreeByNameAPSDControl                     INTEGER,
        gslamAGREL50DegreeByNameAPSDStatus                      INTEGER
	}

	gslamAGREL50DegreeByNameString	OBJECT-TYPE
		SYNTAX		OCTET STRING(SIZE(1..63))
		MAX-ACCESS	not-accessible
		STATUS		current
		DESCRIPTION
			"Degree name identifier for an optical degree interface."
	    ::= { gslamAGREL50DegreeByNameEntry 1 }

	gslamAGREL50DegreeByNameDegreeId	OBJECT-TYPE
		SYNTAX		Unsigned32
       	MAX-ACCESS  read-only
		STATUS		current
		DESCRIPTION
			"Degree interface id for an optical interface."
	    ::= { gslamAGREL50DegreeByNameEntry 2 }

	gslamAGREL50DegreeByNameOSC	OBJECT-TYPE
		SYNTAX		FlagValue
       	MAX-ACCESS  read-only
		STATUS		current
		DESCRIPTION
			"Indicate if optical interface provides the
			 Optical Supervisory Channel "
	    ::= { gslamAGREL50DegreeByNameEntry 3 }

	gslamAGREL50DegreeByNameAmplificationConfig	OBJECT-TYPE
		SYNTAX		AmplificationConfigModeValue
       	MAX-ACCESS  read-only
		STATUS		current
		DESCRIPTION
			"Defines the optical amplifier configuration for the interface "
	    ::= { gslamAGREL50DegreeByNameEntry 4 }

	gslamAGREL50DegreeByNameNominalPerChnlOPPwr  OBJECT-TYPE
       	SYNTAX      OCTET STRING(SIZE(1..63))
       	MAX-ACCESS  read-only
       	STATUS      current
       	DESCRIPTION
           	" The nominal per channel output power for the degree.
                 -17.0 to +13.0 (dBm). Default Value = 1"
       	::= { gslamAGREL50DegreeByNameEntry 5 }

	gslamAGREL50DegreeByNameNtwkFibType	OBJECT-TYPE
       	SYNTAX      INTEGER {
       		unknown(1),
       		g652(2),
       		g653(3),
       		g655(4)
    	}        	
       	MAX-ACCESS  read-only
       	STATUS      deprecated 
       	DESCRIPTION
    		"This is the fiber type. Default is G652"
       	::= { gslamAGREL50DegreeByNameEntry 6 }

	gslamAGREL50DegreeByNameTotalDispersion OBJECT-TYPE
       	SYNTAX      INTEGER (-1500..3000)
       	MAX-ACCESS  read-only
       	STATUS      current
       	DESCRIPTION
           	" The optical total dispersion.
			 -1500 to 3000 (ps/nm). Default Value = 1. No Default"
       	::= { gslamAGREL50DegreeByNameEntry 7 }

    gslamAGREL50DegreeByNameNtwkFibType2 OBJECT-TYPE
        SYNTAX      INTEGER {
            unknown(1),
            unprovisioned(2),
            g652(3),
            g653(4),
            g655EL(5),
            g655LS(6),
            g655TW(7)
        }
        MAX-ACCESS  read-only
        STATUS      current
        DESCRIPTION
            "This is the fiber type. Default is unprovisioned"
        ::= { gslamAGREL50DegreeByNameEntry 8 }

    gslamAGREL50DegreeByNameNtwkFibLen OBJECT-TYPE
        SYNTAX      INTEGER (0..200)
        MAX-ACCESS  read-only
        STATUS      current
        DESCRIPTION
            "This is the fiber length. Default is 0"
        ::= { gslamAGREL50DegreeByNameEntry 9 }

     gslamAGREL50DegreeByNameAPSDControl OBJECT-TYPE
        SYNTAX      INTEGER {
            unknown (1),
            enabled (2),
            disabled (3),
            manrestart(4)
        }
        MAX-ACCESS  read-only
        STATUS      current
        DESCRIPTION
            "This is APSD control. Default is enabled"
        ::= { gslamAGREL50DegreeByNameEntry 10 }

    gslamAGREL50DegreeByNameAPSDStatus OBJECT-TYPE
        SYNTAX      INTEGER {
            unknown (1),
            shutdown (2),
            shutdown-fail (3),
            normal(4)
        }
        MAX-ACCESS  read-only
        STATUS      current
        DESCRIPTION
            "This is APSD status"
        ::= { gslamAGREL50DegreeByNameEntry 11 }

	-- *********** R5.0 RTRV-TOPOLOGY *******************
	gslamAGREL50TopologyTable	OBJECT-TYPE
		SYNTAX		SEQUENCE OF GslamAGREL50TopologyEntry
		MAX-ACCESS	not-accessible
		STATUS		current
		DESCRIPTION
			"A table about the current status of
			 all optical topologies in the GSLAM-AG."
	    ::= { ipiGslamAGREL50TopologyObjs 1 }

	gslamAGREL50TopologyEntry OBJECT-TYPE
		SYNTAX  		GslamAGREL50TopologyEntry
		MAX-ACCESS		not-accessible
		STATUS  		current
		DESCRIPTION
			"A row in the GSLAM-AG Optical Topology table."
		INDEX { gslamAGREL50TopologyShelf,gslamAGREL50TopologyModule,
				gslamAGREL50TopologyPort, gslamAGREL50TopologyChnl }
	    ::= { gslamAGREL50TopologyTable 1 }

	GslamAGREL50TopologyEntry ::= SEQUENCE {
		gslamAGREL50TopologyShelf		Unsigned32,
		gslamAGREL50TopologyModule		Unsigned32,
		gslamAGREL50TopologyPort		Unsigned32,
		gslamAGREL50TopologyChnl		Unsigned32,
		gslamAGREL50TopologyDir			INTEGER,
		gslamAGREL50TopologyRX        	OCTET STRING,
		gslamAGREL50TopologyTX        	OCTET STRING,
		gslamAGREL50TopologyProtectionInfo		INTEGER,
		gslamAGREL50TopologyRXProtection   	OCTET STRING,
		gslamAGREL50TopologyTXProtection   	OCTET STRING
	}

	gslamAGREL50TopologyShelf OBJECT-TYPE
       	SYNTAX      Unsigned32
       	MAX-ACCESS  not-accessible
       	STATUS      current
       	DESCRIPTION
			"The src shelf aid"
       	::= { gslamAGREL50TopologyEntry 1 }

	gslamAGREL50TopologyModule OBJECT-TYPE
       	SYNTAX      Unsigned32
       	MAX-ACCESS  not-accessible
       	STATUS      current
       	DESCRIPTION
			"The src module aid"
       	::= { gslamAGREL50TopologyEntry 2 }

	gslamAGREL50TopologyPort OBJECT-TYPE
       	SYNTAX      Unsigned32
       	MAX-ACCESS  not-accessible
       	STATUS      current
       	DESCRIPTION
			"The src port aid"
       	::= { gslamAGREL50TopologyEntry 3 }

	gslamAGREL50TopologyChnl OBJECT-TYPE
       	SYNTAX      Unsigned32
       	MAX-ACCESS  not-accessible
       	STATUS      current
       	DESCRIPTION
			"The src chnl aid"
       	::= { gslamAGREL50TopologyEntry 4 }

	gslamAGREL50TopologyDir OBJECT-TYPE
		SYNTAX  INTEGER {
            unknown(1),
            not-applicable(2),
            none(3),
            rx(4),
            tx(5),
            rx-tx(6)
        }
       	MAX-ACCESS  read-only
       	STATUS      current
       	DESCRIPTION
			"The direction aid"
       	::= { gslamAGREL50TopologyEntry 5 }

	gslamAGREL50TopologyRX OBJECT-TYPE
        SYNTAX      OCTET STRING(SIZE(0..4096))
       	MAX-ACCESS  read-only
       	STATUS      current
       	DESCRIPTION
			"The RX side topology chain. It contains the following
				(inporttype-shelf-module-port,
					Device,
					Degree,
					Dcmtype,
					Dispersion,
					padval,
					out-porttype-shelf-module-port)+|
				where portype is a numeric val,
					  shelf,module and port is numeric val,
					  device is either F for Fiber or numeric val for a module
					  Degree is numeric
					  Dcmtype is numeric
					  Dispersion is numeric
					  padval is numeric
				For example for a RX chain like,
				N-1X2-3Y4-N
			 The value contained in this would be something like
				N,F,1,1,10,0,X-1-2-1|X-1-2-1,ModType,0,0,0,0,X-1-2-2|..."
       	::= { gslamAGREL50TopologyEntry 6 }

	gslamAGREL50TopologyTX OBJECT-TYPE
        SYNTAX      OCTET STRING(SIZE(0..4096))
       	MAX-ACCESS  read-only
       	STATUS      current
       	DESCRIPTION
			"The TX side topology chain. It contains the following
				(inporttype-shelf-module-port,
					Device,
					Degree,
					Dcmtype,
					Dispersion,
					padval,
					out-porttype-shelf-module-port)+|
				where portype is a numeric val,
					  shelf,module and port is numeric val,
					  device is either F for Fiber or numeric val for a module
					  Degree is numeric
					  Dcmtype is numeric
					  Dispersion is numeric
					  padval is numeric
				For example for a TX chain like,
				N-1X2-3Y4-N
			 The value contained in this would be something like
				N,F,1,1,10,0,X-1-2-1|X-1-2-1,Mod enum,0,0,0,0,0,X-1-2-2|..."
       	::= { gslamAGREL50TopologyEntry 7 }

	gslamAGREL50TopologyProtectionInfo OBJECT-TYPE
		SYNTAX  INTEGER {
			unknown(0),
            no(1),
            yes(2)
        }
       	MAX-ACCESS  read-only
       	STATUS      current
       	DESCRIPTION
			"This provides info to NE if protection data is to be 
			 provided (yes) or not. Working data is always provided. "
       	::= { gslamAGREL50TopologyEntry 8 }

	gslamAGREL50TopologyRXProtection OBJECT-TYPE
        SYNTAX      OCTET STRING(SIZE(0..4096))
       	MAX-ACCESS  read-only
       	STATUS      current
       	DESCRIPTION
			"The RX side protection topology chain. It contains the following
				(inporttype-shelf-module-port,
					Device,
					Degree,
					Dcmtype,
					Dispersion,
					padval,
					out-porttype-shelf-module-port)+|
				where portype is a numeric val,
					  shelf,module and port is numeric val,
					  device is either F for Fiber or numeric val for a module
					  Degree is numeric
					  Dcmtype is numeric
					  Dispersion is numeric
					  padval is numeric
				For example for a RX chain like,
				N-1X2-3Y4-N
			 The value contained in this would be something like
				N,F,1,1,10,0,X-1-2-1|X-1-2-1,ModType,0,0,0,0,X-1-2-2|..."
       	::= { gslamAGREL50TopologyEntry 9 }

	gslamAGREL50TopologyTXProtection OBJECT-TYPE
        SYNTAX      OCTET STRING(SIZE(0..4096))
       	MAX-ACCESS  read-only
       	STATUS      current
       	DESCRIPTION
			"The TX side topology chain. It contains the following
				(inporttype-shelf-module-port,
					Device,
					Degree,
					Dcmtype,
					Dispersion,
					padval,
					out-porttype-shelf-module-port)+|
				where portype is a numeric val,
					  shelf,module and port is numeric val,
					  device is either F for Fiber or numeric val for a module
					  Degree is numeric
					  Dcmtype is numeric
					  Dispersion is numeric
					  padval is numeric
				For example for a TX chain like,
				N-1X2-3Y4-N
			 The value contained in this would be something like
				N,F,1,1,10,0,X-1-2-1|X-1-2-1,Mod enum,0,0,0,0,0,X-1-2-2|..."
       	::= { gslamAGREL50TopologyEntry 10}

	-- ROADM 5.0 START
	gslamAGREL50ROADMPortAssocTable	OBJECT-TYPE
		SYNTAX		SEQUENCE OF GslamAGREL50ROADMPortAssocEntry
		MAX-ACCESS	not-accessible
		STATUS		current
		DESCRIPTION
			"A table about the current status of
			 all optical degrees in the GSLAM-AG."
		::= { ipiGslamAGREL50ROADMPortAssocObjs 1 }

	gslamAGREL50ROADMPortAssocEntry OBJECT-TYPE
		SYNTAX  		GslamAGREL50ROADMPortAssocEntry
		MAX-ACCESS		not-accessible
		STATUS  		current
		DESCRIPTION
			"A row in the GSLAM-AG Port Association table."
		INDEX { gslamAGREL50ROADMPortAssocSrcShelf,gslamAGREL50ROADMPortAssocSrcSlot,
				gslamAGREL50ROADMPortAssocSrcPort,gslamAGREL50ROADMPortAssocDstShelf, 
				gslamAGREL50ROADMPortAssocDstSlot, gslamAGREL50ROADMPortAssocDstPort }
	    ::= { gslamAGREL50ROADMPortAssocTable 1 }

	GslamAGREL50ROADMPortAssocEntry ::= SEQUENCE {
		gslamAGREL50ROADMPortAssocSrcShelf  		Unsigned32,
		gslamAGREL50ROADMPortAssocSrcSlot			Unsigned32,
		gslamAGREL50ROADMPortAssocSrcPort			Unsigned32,
		gslamAGREL50ROADMPortAssocDstShelf			Unsigned32,
		gslamAGREL50ROADMPortAssocDstSlot			Unsigned32,
		gslamAGREL50ROADMPortAssocDstPort			Unsigned32,
		gslamAGREL50ROADMPortAssocRowStatus    	RowStatus,
		gslamAGREL50ROADMPortAssocType				INTEGER,
		gslamAGREL50ROADMPortAssocDCMDispersion		DispValue,
		gslamAGREL50ROADMPortAssocDCMType			INTEGER,
		gslamAGREL50ROADMPortAssocPadAttenuation	INTEGER
	}
	
	gslamAGREL50ROADMPortAssocSrcShelf  OBJECT-TYPE
        SYNTAX      Unsigned32
        MAX-ACCESS  not-accessible
        STATUS      current
        DESCRIPTION
            "The src shelf of the port association."
        ::= { gslamAGREL50ROADMPortAssocEntry  1 }
	
	gslamAGREL50ROADMPortAssocSrcSlot  OBJECT-TYPE
        SYNTAX      Unsigned32
        MAX-ACCESS  not-accessible
        STATUS      current
        DESCRIPTION
            "The src slot of the port association."
        ::= { gslamAGREL50ROADMPortAssocEntry  2 }

	gslamAGREL50ROADMPortAssocSrcPort  OBJECT-TYPE
        SYNTAX      Unsigned32
        MAX-ACCESS  not-accessible
        STATUS      current
        DESCRIPTION
            "The src port of the port association."
        ::= { gslamAGREL50ROADMPortAssocEntry  3 }
	
	gslamAGREL50ROADMPortAssocDstShelf  OBJECT-TYPE
        SYNTAX      Unsigned32
        MAX-ACCESS  not-accessible
        STATUS      current
        DESCRIPTION
            "The dst shelf of the port association."
        ::= { gslamAGREL50ROADMPortAssocEntry  4 }
	
	gslamAGREL50ROADMPortAssocDstSlot  OBJECT-TYPE
        SYNTAX      Unsigned32
        MAX-ACCESS  not-accessible
        STATUS      current
        DESCRIPTION
            "The dst slot of the port association."
        ::= { gslamAGREL50ROADMPortAssocEntry  5 }

	gslamAGREL50ROADMPortAssocDstPort  OBJECT-TYPE
        SYNTAX      Unsigned32
        MAX-ACCESS  not-accessible
        STATUS      current
        DESCRIPTION
            "The Dst Port of the port association."
        ::= { gslamAGREL50ROADMPortAssocEntry  6 }

	gslamAGREL50ROADMPortAssocRowStatus        OBJECT-TYPE
        SYNTAX      RowStatus
        MAX-ACCESS  read-create
        STATUS      current
        DESCRIPTION
            "Current status of this GSLAM-AG Port Association entry."
        ::= { gslamAGREL50ROADMPortAssocEntry 7 }

	gslamAGREL50ROADMPortAssocType	OBJECT-TYPE
       	SYNTAX      INTEGER {
       		unknown(1),
       		uni-dir(2),
       		bi-dir(3)
    	}        	
		MAX-ACCESS  read-write
       	STATUS      current
       	DESCRIPTION
    		"This is the port association type. Default is bi-directional.
			 For unidirection, traffic goes from src to dest."
       	::= { gslamAGREL50ROADMPortAssocEntry 8 }

	gslamAGREL50ROADMPortAssocDCMDispersion	OBJECT-TYPE
		SYNTAX DispValue
		MAX-ACCESS  read-write
       	STATUS     deprecated 
       	DESCRIPTION
    		"This is the port association Pad Attenuation in db. 
					Default is 0db"
       	::= { gslamAGREL50ROADMPortAssocEntry 9 }

	gslamAGREL50ROADMPortAssocDCMType	OBJECT-TYPE
       	SYNTAX      INTEGER {
       		dcm0(0),
			dcm3(1),
			dcmp(2),
       		none(3)
    	}        	
		MAX-ACCESS  read-write
       	STATUS      deprecated 
       	DESCRIPTION
    		"This is the port association DCM type. Default is none"
       	::= { gslamAGREL50ROADMPortAssocEntry 10 }

	gslamAGREL50ROADMPortAssocPadAttenuation	OBJECT-TYPE
       	SYNTAX      INTEGER(0..20)
		MAX-ACCESS  read-write
       	STATUS      current
       	DESCRIPTION
    		"This is the port association Pad Association. Default is 0db"
       	::= { gslamAGREL50ROADMPortAssocEntry 11 }

	-- ROADM 5.0 END

	-- This table is for classic chasis, introduced in relesase 5.0.1

	gslamAGTopologyTable	OBJECT-TYPE
		SYNTAX		SEQUENCE OF GslamAGTopologyEntry
		MAX-ACCESS	not-accessible
		STATUS		current
		DESCRIPTION
			"A table about the current status of
			 all optical topologies in the GSLAM-AG."
	    ::= { ipiGslamAGTopologyObjs 1 }

	gslamAGTopologyEntry OBJECT-TYPE
		SYNTAX  		GslamAGTopologyEntry
		MAX-ACCESS		not-accessible
		STATUS  		current
		DESCRIPTION
			"A row in the GSLAM-AG Optical Topology table."
		INDEX { gslamAGTopologyShelf,gslamAGTopologyModule,
                gslamAGTopologyPort, gslamAGTopologyChnl}
	    ::= { gslamAGTopologyTable 1 }

	GslamAGTopologyEntry ::= SEQUENCE {
        gslamAGTopologyShelf        Unsigned32,
        gslamAGTopologyModule       Unsigned32,
        gslamAGTopologyPort     Unsigned32,
        gslamAGTopologyChnl     Unsigned32,
		gslamAGTopologyDir			INTEGER,
		gslamAGTopologyRX        		OCTET STRING,
		gslamAGTopologyTX        		OCTET STRING,
		gslamAGTopologyProtectionInfo		INTEGER,
		gslamAGTopologyRXProtection   	OCTET STRING,
		gslamAGTopologyTXProtection   	OCTET STRING
	}

    gslamAGTopologyShelf OBJECT-TYPE
            SYNTAX      Unsigned32
            MAX-ACCESS  not-accessible
            STATUS      current
            DESCRIPTION
            "The src shelf aid"
            ::= { gslamAGTopologyEntry 1 }

    gslamAGTopologyModule OBJECT-TYPE
            SYNTAX      Unsigned32
            MAX-ACCESS  not-accessible
            STATUS      current
            DESCRIPTION
            "The src module aid"
        ::= { gslamAGTopologyEntry 2 }

    gslamAGTopologyPort OBJECT-TYPE
        SYNTAX      Unsigned32
        MAX-ACCESS  not-accessible
        STATUS      current
        DESCRIPTION
            "The src port aid"
        ::= { gslamAGTopologyEntry 3 }

    gslamAGTopologyChnl OBJECT-TYPE
        SYNTAX      Unsigned32
        MAX-ACCESS  not-accessible
        STATUS      current
        DESCRIPTION
            "The src chnl aid"
        ::= { gslamAGTopologyEntry 4 }

	gslamAGTopologyDir OBJECT-TYPE
		SYNTAX  INTEGER {
            unknown(1),
            not-applicable(2),
            none(3),
            rx(4),
            tx(5),
            rx-tx(6)
        }
       	MAX-ACCESS  read-only
       	STATUS      current
       	DESCRIPTION
			"The direction aid"
       	::= { gslamAGTopologyEntry 5 }

	gslamAGTopologyRX OBJECT-TYPE
        SYNTAX      OCTET STRING(SIZE(0..4096))
       	MAX-ACCESS  read-only
       	STATUS      current
       	DESCRIPTION
			"The RX side topology chain. It contains the following
				(inporttype-portIfIndex,
					Device,
					Degree,
					Dcmtype,
					Dispersion,
					padval,
					out-porttype-portIfIndex)+|
				where portype is a numeric val,
					  portIfIndex is a numeric val,
					  device is either F for Fiber or numeric val for a module
					  Degree is numeric
					  Dcmtype is numeric
					  Dispersion is numeric
					  padval is numeric
				For example for a RX chain like,
				N-1X2-3Y4-N
			 The value contained in this would be something like
				N,F,1,1,10,0,X-Y|X-Y,ModType,0,0,0,0,X-Y'|..."
       	::= { gslamAGTopologyEntry 6 }

	gslamAGTopologyTX OBJECT-TYPE
        SYNTAX      OCTET STRING(SIZE(0..4096))
       	MAX-ACCESS  read-only
       	STATUS      current
       	DESCRIPTION
			"The TX side topology chain. It contains the following
				(inporttype-portIfIndex,
					Device,
					Degree,
					Dcmtype,
					Dispersion,
					padval,
					out-porttype-portIfIndex)+|
				where portype is a numeric val,
					  portIfIndex is a numeric val,
					  device is either F for Fiber or numeric val for a module
					  Degree is numeric
					  Dcmtype is numeric
					  Dispersion is numeric
					  padval is numeric
				For example for a TX chain like,
				N-1X2-3Y4-N
			 The value contained in this would be something like
				N,F,1,1,10,0,X-Y|X-Y,ModType,0,0,0,0,0,X-Y'|..."
       	::= { gslamAGTopologyEntry 7 }

	gslamAGTopologyProtectionInfo OBJECT-TYPE
		SYNTAX  INTEGER {
			unknown(0),
            no(1),
            yes(2)
        }
       	MAX-ACCESS  read-only
       	STATUS      current
       	DESCRIPTION
			"This provides info to NE if protection data is to be 
			 provided (yes) or not. Working data is always provided. "
       	::= { gslamAGTopologyEntry 8 }

	gslamAGTopologyRXProtection OBJECT-TYPE
        SYNTAX      OCTET STRING(SIZE(0..4096))
       	MAX-ACCESS  read-only
       	STATUS      current
       	DESCRIPTION
			"The RX side protection topology chain. It contains the following
				(inporttype-portIfIndex ,
					Device,
					Degree,
					Dcmtype,
					Dispersion,
					padval,
					out-porttype-portIfIndex )+|
				where portype is a numeric val,
					  portIfIndex is numeric val,
					  device is either F for Fiber or numeric val for a module
					  Degree is numeric
					  Dcmtype is numeric
					  Dispersion is numeric
					  padval is numeric
				For example for a RX chain like,
				N-1X2-3Y4-N
			 The value contained in this would be something like
				N,F,1,1,10,0,X-Y|X-Y,ModType,0,0,0,0,X-Y'|..."
       	::= { gslamAGTopologyEntry 9 }

	gslamAGTopologyTXProtection OBJECT-TYPE
        SYNTAX      OCTET STRING(SIZE(0..4096))
       	MAX-ACCESS  read-only
       	STATUS      current
       	DESCRIPTION
			"The TX side topology chain. It contains the following
				(inporttype-portIfIndex ,
					Device,
					Degree,
					Dcmtype,
					Dispersion,
					padval,
					out-porttype-portIfIndex )+|
				where portype is a numeric val,
					  portIfIndex is numeric val,
					  device is either F for Fiber or numeric val for a module
					  Degree is numeric
					  Dcmtype is numeric
					  Dispersion is numeric
					  padval is numeric
				For example for a TX chain like,
				N-1X2-3Y4-N
			 The value contained in this would be something like
				N,F,1,1,10,0,X-Y|X-Y,ModType,0,0,0,0,0,X-Y'|..."
       	::= { gslamAGTopologyEntry 10}

	
	gslamAGPortAssocTable	OBJECT-TYPE
		SYNTAX		SEQUENCE OF GslamAGPortAssocEntry
		MAX-ACCESS	not-accessible
		STATUS		current
		DESCRIPTION
			"A table about the current status of
			 all optical degrees in the GSLAM-AG."
		::= { ipiGslamAGPortAssocObjs 1 }

	gslamAGPortAssocEntry OBJECT-TYPE
		SYNTAX  		GslamAGPortAssocEntry
		MAX-ACCESS		not-accessible
		STATUS  		current
		DESCRIPTION
			"A row in the GSLAM-AG Port Association table."
		INDEX { gslamAGPortAssocSrcShelf,gslamAGPortAssocSrcSlot,
                gslamAGPortAssocSrcPort,gslamAGPortAssocDstShelf,
                gslamAGPortAssocDstSlot, gslamAGPortAssocDstPort}
	    ::= { gslamAGPortAssocTable 1 }

	GslamAGPortAssocEntry ::= SEQUENCE {
        gslamAGPortAssocSrcShelf        Unsigned32,
        gslamAGPortAssocSrcSlot         Unsigned32,
        gslamAGPortAssocSrcPort         Unsigned32,
        gslamAGPortAssocDstShelf        Unsigned32,
        gslamAGPortAssocDstSlot         Unsigned32,
        gslamAGPortAssocDstPort         Unsigned32,
		gslamAGPortAssocSrcIfIndex		Unsigned32,
		gslamAGPortAssocDstIfIndex		Unsigned32,
		gslamAGPortAssocRowStatus    		RowStatus,
		gslamAGPortAssocType			INTEGER,
		gslamAGPortAssocDCMDispersion		DispValue,
		gslamAGPortAssocDCMType			INTEGER,
		gslamAGPortAssocPadAttenuation		INTEGER
	}

    gslamAGPortAssocSrcShelf  OBJECT-TYPE
        SYNTAX      Unsigned32
        MAX-ACCESS  not-accessible
        STATUS      current
        DESCRIPTION
            "The src shelf of the port association."
        ::= { gslamAGPortAssocEntry  1 }

    gslamAGPortAssocSrcSlot  OBJECT-TYPE
        SYNTAX      Unsigned32
        MAX-ACCESS  not-accessible
        STATUS      current
        DESCRIPTION
            "The src slot of the port association."
        ::= { gslamAGPortAssocEntry  2 }

    gslamAGPortAssocSrcPort  OBJECT-TYPE
        SYNTAX      Unsigned32
        MAX-ACCESS  not-accessible
        STATUS      current
        DESCRIPTION
            "The src port of the port association."
        ::= { gslamAGPortAssocEntry  3 }

    gslamAGPortAssocDstShelf  OBJECT-TYPE
        SYNTAX      Unsigned32
        MAX-ACCESS  not-accessible
        STATUS      current
        DESCRIPTION
            "The dst shelf of the port association."
        ::= { gslamAGPortAssocEntry  4 }
    gslamAGPortAssocDstSlot  OBJECT-TYPE
        SYNTAX      Unsigned32
        MAX-ACCESS  not-accessible
        STATUS      current
        DESCRIPTION
            "The dst slot of the port association."
        ::= { gslamAGPortAssocEntry  5 }

    gslamAGPortAssocDstPort  OBJECT-TYPE
        SYNTAX      Unsigned32
        MAX-ACCESS  not-accessible
        STATUS      current
        DESCRIPTION
            "The Dst Port of the port association."
        ::= { gslamAGPortAssocEntry  6 }
	
	gslamAGPortAssocSrcIfIndex OBJECT-TYPE
        SYNTAX      Unsigned32
        MAX-ACCESS  read-only
        STATUS      current
        DESCRIPTION
            "The src shelf of the port association."
        ::= { gslamAGPortAssocEntry  7 }
	
	gslamAGPortAssocDstIfIndex OBJECT-TYPE
        SYNTAX      Unsigned32
        MAX-ACCESS  read-only
        STATUS      current
        DESCRIPTION
            "The dst shelf of the port association."
        ::= { gslamAGPortAssocEntry  8 }
	
	gslamAGPortAssocRowStatus        OBJECT-TYPE
        SYNTAX      RowStatus
        MAX-ACCESS  read-create
        STATUS      current
        DESCRIPTION
            "Current status of this GSLAM-AG Port Association entry."
        ::= { gslamAGPortAssocEntry 9 }

	gslamAGPortAssocType	OBJECT-TYPE
       	SYNTAX      INTEGER {
       		unknown(1),
       		uni-dir(2),
       		bi-dir(3)
    	}        	
		MAX-ACCESS  read-write
       	STATUS      current
       	DESCRIPTION
    		"This is the port association type. Default is bi-directional.
			 For unidirection, traffic goes from src to dest."
       	::= { gslamAGPortAssocEntry 10 }

	gslamAGPortAssocDCMDispersion	OBJECT-TYPE
		SYNTAX DispValue
		MAX-ACCESS  read-write
       	STATUS      deprecated 
       	DESCRIPTION
    		"This is the port association Pad Attenuation in db. 
					Default is 0db"
       	::= { gslamAGPortAssocEntry 11 }

	gslamAGPortAssocDCMType	OBJECT-TYPE
       	SYNTAX      INTEGER {
       		dcm0(0),
			dcm3(1),
			dcmp(2),
       		none(3)
    	}        	
		MAX-ACCESS  read-write
       	STATUS      deprecated 
       	DESCRIPTION
    		"This is the port association DCM type. Default is none"
       	::= { gslamAGPortAssocEntry 12 }

	gslamAGPortAssocPadAttenuation	OBJECT-TYPE
       	SYNTAX      INTEGER(0..20)
		MAX-ACCESS  read-write
       	STATUS      current
       	DESCRIPTION
    		"This is the port association Pad Association. Default is 0db"
       	::= { gslamAGPortAssocEntry 13 }

	--  5.1 END
	--ROADM 5.0 START
	gslamAGREL50ROADMOpticalCXTable	OBJECT-TYPE
		SYNTAX		SEQUENCE OF GslamAGREL50ROADMOpticalCXEntry
		MAX-ACCESS	not-accessible
		STATUS		current
		DESCRIPTION
			"A table about the current status of all optical Cross-Connects in the GSLAM-AG."
		::= { ipiGslamAGREL50ROADMOpticalCXObjs 1 }

	gslamAGREL50ROADMOpticalCXEntry OBJECT-TYPE
		SYNTAX  		GslamAGREL50ROADMOpticalCXEntry
		MAX-ACCESS		not-accessible
		STATUS  		current
		DESCRIPTION
			"A row in the GSLAM-AG Optical Cross-Connect table."
		INDEX { gslamAGREL50ROADMOpticalCXSrcShelf,gslamAGREL50ROADMOpticalCXSrcSlot,
				gslamAGREL50ROADMOpticalCXSrcPort, gslamAGREL50ROADMOpticalCXSrcChnl,
				gslamAGREL50ROADMOpticalCXDstShelf, gslamAGREL50ROADMOpticalCXDstSlot, 
				gslamAGREL50ROADMOpticalCXDstPort, gslamAGREL50ROADMOpticalCXDstChnl }
	    ::= { gslamAGREL50ROADMOpticalCXTable 1 }

	GslamAGREL50ROADMOpticalCXEntry ::= SEQUENCE {
		gslamAGREL50ROADMOpticalCXSrcShelf 	Unsigned32,
		gslamAGREL50ROADMOpticalCXSrcSlot	Unsigned32,
		gslamAGREL50ROADMOpticalCXSrcPort	Unsigned32, 
		gslamAGREL50ROADMOpticalCXSrcChnl	Unsigned32,
		gslamAGREL50ROADMOpticalCXDstShelf	Unsigned32, 
		gslamAGREL50ROADMOpticalCXDstSlot	Unsigned32, 
		gslamAGREL50ROADMOpticalCXDstPort	Unsigned32,
		gslamAGREL50ROADMOpticalCXDstChnl	Unsigned32, 
		gslamAGREL50ROADMOpticalCXRowStatus  RowStatus,
		gslamAGREL50ROADMOpticalCXDirection	ConnModeValue,
		gslamAGREL50ROADMOpticalCXCktID		OCTET STRING,
		gslamAGREL50ROADMOpticalCXNature    INTEGER,
		gslamAGREL50ROADMOpticalCXItuNumber  Unsigned32,
		gslamAGREL50ROADMOpticalCXsrcDegree  INTEGER,
		gslamAGREL50ROADMOpticalCXdstDegree  INTEGER

	}

	gslamAGREL50ROADMOpticalCXSrcShelf  OBJECT-TYPE
        SYNTAX      Unsigned32
        MAX-ACCESS  not-accessible
        STATUS      current
        DESCRIPTION
            "The src shelf of the Optical Cross-Connect Entry."
        ::= { gslamAGREL50ROADMOpticalCXEntry  1 }

	gslamAGREL50ROADMOpticalCXSrcSlot  OBJECT-TYPE
        SYNTAX      Unsigned32
        MAX-ACCESS  not-accessible
        STATUS      current
        DESCRIPTION
            "The src slot of the Optical Cross-Connect Entry."
        ::= { gslamAGREL50ROADMOpticalCXEntry  2 }

	gslamAGREL50ROADMOpticalCXSrcPort  OBJECT-TYPE
        SYNTAX      Unsigned32
        MAX-ACCESS  not-accessible
        STATUS      current
        DESCRIPTION
            "The src port of the Optical Cross-Connect Entry."
        ::= { gslamAGREL50ROADMOpticalCXEntry  3 }

	gslamAGREL50ROADMOpticalCXSrcChnl  OBJECT-TYPE
        SYNTAX      Unsigned32
        MAX-ACCESS  not-accessible
        STATUS      current
        DESCRIPTION
            "The src channel of the Optical Cross-Connect entry.
			 End channels of the OXCON can be associated with OCH ports on DWR; 
			 OTS ports on OAV; OMS ports on OAV; and ....etc. 
				However the channel index for an OCH port will contain 0 as NE
			 does not support creation of occ channel in an OCH port"
        ::= { gslamAGREL50ROADMOpticalCXEntry  4 }

	gslamAGREL50ROADMOpticalCXDstShelf  OBJECT-TYPE
        SYNTAX      Unsigned32
        MAX-ACCESS  not-accessible
        STATUS      current
        DESCRIPTION
            "The dst shelf of the Optical Cross-Connect Entry."
        ::= { gslamAGREL50ROADMOpticalCXEntry  5 }

	gslamAGREL50ROADMOpticalCXDstSlot  OBJECT-TYPE
        SYNTAX      Unsigned32
        MAX-ACCESS  not-accessible
        STATUS      current
        DESCRIPTION
            "The  dst slot of the Optical Cross-Connect Entry."
        ::= { gslamAGREL50ROADMOpticalCXEntry  6 }

	gslamAGREL50ROADMOpticalCXDstPort  OBJECT-TYPE
        SYNTAX      Unsigned32
        MAX-ACCESS  not-accessible
        STATUS      current
        DESCRIPTION
            "The dst port of the Optical Cross-Connect Entry."
        ::= { gslamAGREL50ROADMOpticalCXEntry  7 }

	gslamAGREL50ROADMOpticalCXDstChnl  OBJECT-TYPE
        SYNTAX      Unsigned32
        MAX-ACCESS  not-accessible
        STATUS      current
        DESCRIPTION
            "The dst channel of the Optical Cross-Connect entry.
			 End channels of the OXCON can be associated with OCH ports on DWR; 
			 OTS ports on OAV; OMS ports on OAV; and ....etc. 
				However the channel index for an OCH port will contain 0 as NE
			 does not support creation of occ channel in an OCH port"
        ::= { gslamAGREL50ROADMOpticalCXEntry  8 }

	gslamAGREL50ROADMOpticalCXRowStatus        OBJECT-TYPE
        SYNTAX      RowStatus
        MAX-ACCESS  read-create
        STATUS      current
        DESCRIPTION
            "Current status of this GSLAM-AG Optical CX entry."
        ::= { gslamAGREL50ROADMOpticalCXEntry 9 }

	gslamAGREL50ROADMOpticalCXDirection    OBJECT-TYPE
        SYNTAX  ConnModeValue
        MAX-ACCESS  read-write
        STATUS      current
        DESCRIPTION
            "Indicates the direction of this Optical CX. For unidirection, 
			 traffic goes from src to dest. Default value is bidirection"
        ::= { gslamAGREL50ROADMOpticalCXEntry 10 }

	gslamAGREL50ROADMOpticalCXCktID        OBJECT-TYPE
        SYNTAX      OCTET STRING(SIZE(0..64))
        MAX-ACCESS  read-write
        STATUS      current
        DESCRIPTION
            "The Circuit ID used for creating this CX, 
				Return empty string if not available."
        ::= { gslamAGREL50ROADMOpticalCXEntry 11 }

	 gslamAGREL50ROADMOpticalCXNature        OBJECT-TYPE
        SYNTAX INTEGER {
            unknown(0),
            user-created(1),
            auto-created(2)
        }
        MAX-ACCESS  read-only
        STATUS      current
        DESCRIPTION
            "The xcon nature, user or auto-created"
        ::= { gslamAGREL50ROADMOpticalCXEntry 12 }

	 gslamAGREL50ROADMOpticalCXItuNumber         OBJECT-TYPE
        SYNTAX Unsigned32
        MAX-ACCESS  read-only
        STATUS      current
        DESCRIPTION	
			"The ITU channel number valid values are integers 16-59 
					except {24,33,42,51}" 
        ::= { gslamAGREL50ROADMOpticalCXEntry 13 }

	 gslamAGREL50ROADMOpticalCXsrcDegree         OBJECT-TYPE
        SYNTAX INTEGER (1..63535)
        MAX-ACCESS  read-write
        STATUS      current
        DESCRIPTION	
			"The src degree of the OXCON" 
        ::= { gslamAGREL50ROADMOpticalCXEntry 14 }

	 gslamAGREL50ROADMOpticalCXdstDegree         OBJECT-TYPE
        SYNTAX INTEGER (1..63535)
        MAX-ACCESS  read-write
        STATUS      current
        DESCRIPTION	
			"The dst degree of the OXCON" 
        ::= { gslamAGREL50ROADMOpticalCXEntry 15 }
	
	-- GslamAG notification helper objects
	cn4200NotificationHelperPEOID	OBJECT-TYPE
		SYNTAX		OBJECT IDENTIFIER
		MAX-ACCESS	not-accessible
		STATUS		current
		DESCRIPTION
			"Used in the variable binding of some gslamAG notification to indicate the OID of
			 the physical entity OR it is the IOD of user for security related alarms involved
			 in the GSLAM-AG notification."
	    ::= { cn4200NotificationHelperObjs 1 }

	cn4200NotificationHelperPEType	OBJECT-TYPE
		SYNTAX		EquipmentTypeValue
		MAX-ACCESS	not-accessible
		STATUS		current
		DESCRIPTION
			"Used in the variable binding of some gslamAG notification to indicate the type of
			 the physical entity involved in the GSLAM-AG notification."
	    ::= { cn4200NotificationHelperObjs 2 }

	cn4200NotificationHelperAction	OBJECT-TYPE
		SYNTAX INTEGER {
			unknown(1),
			not-applicable(2),
			none(3),			-- no action associated with the notification
			set(4),			-- alarm/event set
			clear(5),		-- alarm/event clear
			transient(6),	-- no set/clear condition
			clearall(7)		-- clear all set alarm/event for equipment
		}
		MAX-ACCESS	not-accessible
		STATUS		current
		DESCRIPTION
			"Used in the variable binding of some gslamAG notification to indicate the action
			 in the GSLAM-AG notification."
	    ::= { cn4200NotificationHelperObjs 3 }

	cn4200NotificationHelperSev	OBJECT-TYPE
		SYNTAX INTEGER {
			unknown(1),
			not-present(2),
			inactive(3),
			not-reported(4),
			not-alarmed(5),
			minor(6),
			major(7),
			critical(8)
		}
		MAX-ACCESS	not-accessible
		STATUS		current
		DESCRIPTION
			"Used in the variable binding of some gslamAG notification to indicate the severity
			 in the GSLAM-AG notification."
	    ::= { cn4200NotificationHelperObjs 4 }

	cn4200NotificationMonTypeAndDir OBJECT-TYPE
		SYNTAX INTEGER {
			unknown(1),
			rx-cvl(2),
			rx-esl(3),
			rx-sesl(4),
			rx-uasl(5),
			rx-cvp(6),
			rx-esp(7),
			rx-sesp(8),
			rx-uasp(9),
			tx-cvl(10),
			tx-esl(11),
			tx-sesl(12),
			tx-uasl(13),
			tx-cvp(14),
			tx-esp(15),
			tx-sesp(16),
			tx-uasp(17),
			rx-ovsl(18),
			psc(19),
			rx-invw(20),
			tx-invw(21),
			rx-cv(22),
			rx-es(23),
			rx-ses(24),
			rx-uas(25),
			tx-cv(26),
			tx-es(27),
			tx-ses(28),
			tx-uas(29),
			rx-cvs(30),
			rx-ess(31),
			rx-sess(32),
			rx-uass(33),
			rx-csess(34),
			rx-sefs(35),
			tx-lbc(36),
			rx-opr(37),
			tx-opt(38),
			rx-csesp(39),
			tx-csesp(40),
			rx-bbep(41),
			rx-bbes(42),
			rx-sems(43),
			rx-bbe-sfe(44),
			rx-es-sfe(45),
			rx-ses-sfe(46),
			rx-uas-sfe(47),
			rx-cses-sfe(48),
			rx-bbe-pfe(49),
			rx-es-pfe(50),
			rx-ses-pfe(51),
			rx-uas-pfe(52),
			rx-cses-pfe(53),
			tx-bbe-pfe(54),
			tx-es-pfe(55),
			tx-ses-pfe(56),
			tx-uas-pfe(57),
			tx-cses-pfe(58),
			tx-bbes(59),
			tx-ess(60),
			tx-sess(61),
			tx-uass(62),
			tx-csess(63),
			tx-sefs(64),
			tx-cvs(65),
			rx-ppjc(66),
			rx-npjc(67),
			rx-pjcdiff(68),
			rx-chec(69),
			rx-thec(70),
			rx-dfrm(71),
			rx-sblk(72),
			rx-cses(73),
			tx-cses(74),
			tx-deg(75),
			rx-deg(76),
			rx-cses-fe(77),
			rx-ppjc-ip(78),
			rx-npjc-ip(79),
			rx-pjcdiff-ip(80),
			rx-bbe(81),
			rx-bbe-fe(82),
			rx-es-fe(83),
			rx-ses-fe(84),
			rx-uas-fe(85),
			rx-csesl(86),
			tx-csesl(87),
			pscl(88),
			pscp(89),
			rx-fec(90),
			rx-opr-o(91),
			tx-opt-o(92),
			rx-oslr(93),
			tx-oslt(94),
			tx-lbcp1(95),
			tx-lbcp2(96),
			pscs(97),
			rx-pc(98),
			tx-pc(99),
			lbc-o(100),
			opr-p(101),
			opt-p(102),
			rx-lbcp1l(103),
			tx-lbcp2l(104),
			oslr(105),
			oslt(106),
			rx-sef(107),
			tx-sef(108),
			rx-byte(109),
			tx-byte(110),
			rx-oprs(111),
			tx-opts(112),
            ess-p(113),
            sess-p(114),
            csess-p(115),
            uass-p(116),
            cvss-o(117),
            ess-o(118),
            sess-o(119),
            sefs-o(120),
            csess-o(121),
            uass-o(122),
            ess-pfe(123),
            sess-pfe(124),
            csess-pfe(125),
            uass-pfe(126),
            ess-o-fe(127),
            sess-o-fe(128),
            csess-o-fe(129),
            uass-o-fe(130),
            esl-p(131),
            sesl-p(132),
            csesl-p(133),
            uasl-p(134),
            esl-o(135),
            sesl-o(136),
            csesl-o(137),
            uasl-o(138),
            esl-pfe(139),
            sesl-pfe(140),
            csesl-pfe(141),
            uasl-pfe(142),
            esl-o-fe(143),
            sesl-o-fe(144),
            csesl-o-fe(145),
            uasl-o-fe(146),
            rx-opri(147),
            tx-opti(148)
		}
		MAX-ACCESS	not-accessible
		STATUS		current
		DESCRIPTION
			"Used in the variable binding of some gslamAG notification to indicate the monitor
			 type in the GSLAM-AG notification."
	    ::= { cn4200NotificationHelperObjs 5}


   cn4200NotificationDesc	OBJECT-TYPE
		SYNTAX		OCTET STRING(SIZE(1..128))
		MAX-ACCESS	not-accessible
		STATUS		current
		DESCRIPTION
			"Indicates the detailed description of the gslamAG notification."
	    ::= { cn4200NotificationHelperObjs 6 }


   cn4200NotificationInitLevel	OBJECT-TYPE
		SYNTAX		Unsigned32
		MAX-ACCESS	not-accessible
		STATUS		current
		DESCRIPTION
			"Indicates the initialization level."
	    ::= { cn4200NotificationHelperObjs 7 }

   cn4200NotificationHelperWrkPEOID	OBJECT-TYPE
		SYNTAX		OBJECT IDENTIFIER
		MAX-ACCESS	not-accessible
		STATUS		current
		DESCRIPTION
			"Used in the variable binding of the gslamAG protection switch notification to
			 indicate the OID of the active physical entity involved in the notification."
	    ::= { cn4200NotificationHelperObjs 8 }

	cn4200NotificationHelperStbyPEOID	OBJECT-TYPE
		SYNTAX		OBJECT IDENTIFIER
		MAX-ACCESS	not-accessible
		STATUS		current
		DESCRIPTION
			"Used in the variable binding of the gslamAG protection switch notification to
			 indicate the OID of the standby physical entity involved in the notification."
	    ::= { cn4200NotificationHelperObjs 9 }




	-- The following (5) are added for DB change traps
	cn4200NotificationPEPrimaryState	OBJECT-TYPE
		SYNTAX		PrimaryStateValue
		MAX-ACCESS	not-accessible
		STATUS		current
		DESCRIPTION
			"Indicates the primary state of the physical entity involved in the notification."
	    ::= { cn4200NotificationHelperObjs 10 }

	cn4200NotificationPESecondaryState	OBJECT-TYPE
		SYNTAX		SecondaryStateValue
		MAX-ACCESS	not-accessible
		STATUS		current
		DESCRIPTION
			"Indicates the secondary state of the physical entity involved in the notification."
	    ::= { cn4200NotificationHelperObjs 11 }

	cn4200NotificationSwitchOverMode	OBJECT-TYPE
		SYNTAX INTEGER {
			unknown(1),
			not-present(2),
			normal(3),
			forced(4),
			auto(5)
		}
		MAX-ACCESS	not-accessible
		STATUS		current
		DESCRIPTION
			"Indicates the switch over mode of the protection switch notification."
	    ::= { cn4200NotificationHelperObjs 12 }

	cn4200NotificationSourceEqptAddr	OBJECT-TYPE
		SYNTAX		OBJECT IDENTIFIER
		MAX-ACCESS	not-accessible
		STATUS		current
		DESCRIPTION
			"Indicates the OID of the source equipment address involved in the notification."
	    ::= { cn4200NotificationHelperObjs 13}

	cn4200NotificationDestEqptAddr	OBJECT-TYPE
		SYNTAX		OBJECT IDENTIFIER
		MAX-ACCESS	not-accessible
		STATUS		current
		DESCRIPTION
			"Indicates the OID of the destination equipment address involved in the notification."
	    ::= { cn4200NotificationHelperObjs 14 }


	cn4200NotificationFailureReason	OBJECT-TYPE
		SYNTAX		OCTET STRING(SIZE(1..128))
		MAX-ACCESS	not-accessible
		STATUS		current
		DESCRIPTION
			"Indicates the set failure reason."
	    ::= { cn4200NotificationHelperObjs 15 }

	cn4200NotificationCktID	OBJECT-TYPE
		SYNTAX		OCTET STRING(SIZE(0..64))
		MAX-ACCESS	not-accessible
		STATUS		current
		DESCRIPTION
			"Indicates the circuit ID management application provides when add/dlt crossconnect."
	    ::= { cn4200NotificationHelperObjs 16 }

	cn4200NotificationLPID	OBJECT-TYPE
		SYNTAX		OCTET STRING(SIZE(0..64))
		MAX-ACCESS	not-accessible
		STATUS		current
		DESCRIPTION
			"Indicates the light path ID management application provides when add/dlt crossconnect or protection group."
	    ::= { cn4200NotificationHelperObjs 17 }

	-- the next two defined in MXA first
	cn4200NotificationHelperIfIndex	OBJECT-TYPE
		SYNTAX		Unsigned32
		MAX-ACCESS	not-accessible
		STATUS		current
		DESCRIPTION
			"Used in the variable binding of some gslamAG/mxa notification to indicate the ifIndex of
			 the physical entity involved in the GslamAG/MXA notification."
	    ::= { cn4200NotificationHelperObjs 18 }

	cn4200NotificationHelperNameSvr	OBJECT-TYPE
		SYNTAX		OCTET STRING(SIZE(1..20))
		MAX-ACCESS	not-accessible
		STATUS		current
		DESCRIPTION
			"Indicates the IP address or name of the name server."
	    ::= { cn4200NotificationHelperObjs 20 }

	cn4200NotificationHelperDestNetwork	OBJECT-TYPE
		SYNTAX		IpAddress
		MAX-ACCESS	not-accessible
		STATUS		current
		DESCRIPTION
			"Indicates the IP address the destination network."
	    ::= { cn4200NotificationHelperObjs 21 }

	cn4200NotificationHelperGateway	OBJECT-TYPE
		SYNTAX		IpAddress
		MAX-ACCESS	not-accessible
		STATUS		current
		DESCRIPTION
			"Indicates the gateway IP address."
	    ::= { cn4200NotificationHelperObjs 22 }

	cn4200NotificationHelperNetmask	OBJECT-TYPE
		SYNTAX		IpAddress
		MAX-ACCESS	not-accessible
		STATUS		current
		DESCRIPTION
			"Indicates the value of the network mask."
	    ::= { cn4200NotificationHelperObjs 23 }

	cn4200NotificationHelperMetric	OBJECT-TYPE
		SYNTAX		Unsigned32
		MAX-ACCESS	not-accessible
		STATUS		current
		DESCRIPTION
			"Indicates the metric value of an ECC route."
	    ::= { cn4200NotificationHelperObjs 24 }

	cn4200NotificationHelperSID	OBJECT-TYPE
		SYNTAX		OCTET STRING(SIZE(1..20))
		MAX-ACCESS	not-accessible
		STATUS		current
		DESCRIPTION
			"Indicates the SID value of the NE."
	    ::= { cn4200NotificationHelperObjs 25 }

	cn4200NotificationHelperLocalPEType	OBJECT-TYPE
		SYNTAX		EquipmentTypeValue
		MAX-ACCESS	not-accessible
		STATUS		current
		DESCRIPTION
			"Used in the variable binding of NDP link up/down trap to
			indicate the type of the local physical entity involved."
	    ::= { cn4200NotificationHelperObjs 26}

	cn4200NotificationHelperLocalPEOID	OBJECT-TYPE
		SYNTAX		OBJECT IDENTIFIER
		MAX-ACCESS	not-accessible
		STATUS		current
		DESCRIPTION
			"Used in the variable binding of NDP link up/down trap to
			 indicate the OID of the local physical entity involved."
	    ::= { cn4200NotificationHelperObjs 27}

	cn4200NotificationAffectedLP	OBJECT-TYPE
		SYNTAX		OCTET STRING(SIZE(1..1024))
		MAX-ACCESS	not-accessible
		STATUS		current
		DESCRIPTION
			"Indicates the light path(s) affected by the alarm."
	    ::= { cn4200NotificationHelperObjs 28}

	cn4200NotificationAffectedSourceIP	OBJECT-TYPE
		SYNTAX		IpAddress
		MAX-ACCESS	not-accessible
		STATUS		current
		DESCRIPTION
			"Indicates the light path(s) source IP affected by the alarm."
    	::= { cn4200NotificationHelperObjs 29}

    cn4200NotificationLogName  OBJECT-TYPE
	SYNTAX INTEGER {
	    unknown(1),
	    cmd(2),	 -- command
	    dbchg(3),   -- DB change
	    evt(4),     -- event
	    secu(5),    -- security
	    syslog(6)   -- syslog
	}
	MAX-ACCESS  not-accessible
	STATUS      current
	DESCRIPTION
	    "Used in the variable binding of some mxa notification to indicate the log name
	     in the GSLAM-AG notification."
	::= { cn4200NotificationHelperObjs 30 }

    cn4200NotificationHelperServiceIndicator	OBJECT-TYPE
		SYNTAX INTEGER {
			unknown(1),
			service-affecting(2),
			non-service-affecting(3),
			not-applicable(4)
		}
		MAX-ACCESS	not-accessible
		STATUS		current
		DESCRIPTION
			"Used in the variable binding of some gslamAG notification to indicate the Service Indicator
			 in the GSLAM-AG notification."
	    ::= { cn4200NotificationHelperObjs 31  }

    cn4200NotificationHelperMonValue	OBJECT-TYPE
		SYNTAX		Unsigned32
		MAX-ACCESS	not-accessible
		STATUS		current
		DESCRIPTION
			"Used in the variable binding of some gslamAG notification to indicate
			the monitor value."
	    ::= { cn4200NotificationHelperObjs 32  }

    cn4200NotificationHelperMonThreshold	OBJECT-TYPE
		SYNTAX		Unsigned32
		MAX-ACCESS	not-accessible
		STATUS		current
		DESCRIPTION
			"Used in the variable binding of some gslamAG notification to indicate
			the threshold value."
	    ::= { cn4200NotificationHelperObjs 33  }

    cn4200NotificationHelperPEAID	OBJECT-TYPE
		SYNTAX		OCTET STRING(SIZE(1..128))
		MAX-ACCESS	not-accessible
		STATUS		current
		DESCRIPTION
			"Used in the variable binding of some gslamAG notification to indicate
			the AID of the entity involved in the notification."
	    ::= { cn4200NotificationHelperObjs 34  }

    cn4200NotificationHelperLocalPEAID	OBJECT-TYPE
		SYNTAX		OCTET STRING(SIZE(1..128))
		MAX-ACCESS	not-accessible
		STATUS		current
		DESCRIPTION
			"Used in the variable binding of some gslamAG notification to indicate
			the AID of the lcoal entity involved in the notification."
	    ::= { cn4200NotificationHelperObjs 35  }

    cn4200NotificationHelperWrkPEAID	OBJECT-TYPE
		SYNTAX		OCTET STRING(SIZE(1..128))
		MAX-ACCESS	not-accessible
		STATUS		current
		DESCRIPTION
			"Used in the variable binding of some gslamAG notification to indicate
			the AID of the active entity involved in the notification."
	    ::= { cn4200NotificationHelperObjs 36  }

    cn4200NotificationHelperStbyPEAID	OBJECT-TYPE
		SYNTAX		OCTET STRING(SIZE(1..128))
		MAX-ACCESS	not-accessible
		STATUS		current
		DESCRIPTION
			"Used in the variable binding of some gslamAG notification to indicate
			the AID of the standby entity involved in the notification."
	    ::= { cn4200NotificationHelperObjs 37  }

    cn4200NotificationHelperRemotePEAID	OBJECT-TYPE
		SYNTAX		OCTET STRING(SIZE(1..128))
		MAX-ACCESS	not-accessible
		STATUS		current
		DESCRIPTION
			"Used in the variable binding of some gslamAG notification to indicate
			the AID of the remote entity involved in the notification."
	    ::= { cn4200NotificationHelperObjs 38  }

	cn4200NotificationHelperPETypeSrc	OBJECT-TYPE
		SYNTAX		EquipmentTypeValue
		MAX-ACCESS	not-accessible
		STATUS		current
		DESCRIPTION
			"Used in the variable binding of some gslamAG notification to indicate the type of
			 the physical entity involved, as source, in the GSLAM-AG notification."
	    ::= { cn4200NotificationHelperObjs 39 }

	cn4200NotificationHelperPETypeDst	OBJECT-TYPE
		SYNTAX		EquipmentTypeValue
		MAX-ACCESS	not-accessible
		STATUS		current
		DESCRIPTION
			"Used in the variable binding of some gslamAG notification to indicate the type of
			 the physical entity involved, as destination, in the GSLAM-AG notification."
	    ::= { cn4200NotificationHelperObjs 40 }

    cn4200NotificationHelperPEAIDSrc	OBJECT-TYPE
		SYNTAX		OCTET STRING(SIZE(1..128))
		MAX-ACCESS	not-accessible
		STATUS		current
		DESCRIPTION
			"Used in the variable binding of some gslamAG notification to indicate
			the AID of the entity involved, as source, in the notification."
	    ::= { cn4200NotificationHelperObjs 41  }

    cn4200NotificationHelperPEAIDDst	OBJECT-TYPE
		SYNTAX		OCTET STRING(SIZE(1..128))
		MAX-ACCESS	not-accessible
		STATUS		current
		DESCRIPTION
			"Used in the variable binding of some gslamAG notification to indicate
			the AID of the entity involved, as source, in the notification."
	    ::= { cn4200NotificationHelperObjs 42  }

    cn4200NotificationHelperConfigChangeSeqNum      OBJECT-TYPE
                SYNTAX          Unsigned32
                MAX-ACCESS      not-accessible
                STATUS          current
                DESCRIPTION
                        "Used in the variable binding of gslamAG notifications to indicate
                         sequence number for configuration changes."
            ::= { cn4200NotificationHelperObjs 43  }

   cn4200NotificationHelperAlarmType   OBJECT-TYPE
        SYNTAX      OCTET STRING(SIZE(1..128))
        MAX-ACCESS  not-accessible
        STATUS      current
        DESCRIPTION
            "Indicates the alarm type in the gslamAG notification."
        ::= { cn4200NotificationHelperObjs 44 }

   cn4200NotificationHelperAdminState   OBJECT-TYPE
        SYNTAX      INTEGER {
							disabled (0),
							enabled (1)
							}
        MAX-ACCESS  not-accessible
        STATUS      current
        DESCRIPTION
            "Indicates the service status."
        ::= { cn4200NotificationHelperObjs 45 }

   cn4200NotificationHelperDaemon   OBJECT-TYPE
        SYNTAX      INTEGER {
							snmp (0),
							ntp (1),
							http (2),
							tl1 (3),
							gated (4),
							tapimgr1 (5),
							tapimgr2 (6),
							tapimgr3 (7),
							tapimgr4 (8),
							tapimgr5 (9),
							tapimgr6 (10),
							tapimgr7 (11),
							tapimgr8 (12),
							proxyarp (13),
							https (14),
							sshdCli (15),
							sshdTl1 (16),
							secuApp (17),
							sshd (18),
							ssl (19),
							tls (20),
							tl1Proxy (21)
							}
        MAX-ACCESS  not-accessible
        STATUS      current
        DESCRIPTION
            "Indicates the service/daemon."
        ::= { cn4200NotificationHelperObjs 46 }


	-- GslamAG Notifications

	cn4200NotificationAIS		NOTIFICATION-TYPE
		OBJECTS		{
			cn4200NotificationHelperPEOID, cn4200NotificationHelperPEType,
			cn4200NotificationHelperAction, cn4200NotificationHelperSev,
			cn4200NotificationDesc,
			cn4200NotificationHelperServiceIndicator,
			cn4200NotificationAffectedLP, cn4200NotificationAffectedSourceIP,
			cn4200NotificationHelperPEAID, cn4200NotificationHelperConfigChangeSeqNum
		}
		STATUS	current
		DESCRIPTION
			"The alarm indication signal detected/cleared."
		::= { cn4200Notifications 1 }

	cn4200NotificationBATTERY		NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
			"Battery failure/cleared."
		::= { cn4200Notifications 2 }

    cn4200NotificationCGM      NOTIFICATION-TYPE
	OBJECTS     {
	    cn4200NotificationHelperPEOID, cn4200NotificationHelperPEType,
	    cn4200NotificationHelperAction, cn4200NotificationHelperSev,
	    cn4200NotificationDesc,
	    cn4200NotificationHelperServiceIndicator,
	    cn4200NotificationAffectedLP, cn4200NotificationAffectedSourceIP,
		cn4200NotificationHelperPEAID, cn4200NotificationHelperConfigChangeSeqNum
	}
	STATUS  current
	DESCRIPTION
	    "Concatenation group mismatch."
	::= { cn4200Notifications 3 }

	cn4200NotificationCLFAN		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperConfigChangeSeqNum
		}
		STATUS	current
		DESCRIPTION
			"Cooling fan failure/cleared."
		::= { cn4200Notifications 4 }

    -- DEG => SDBER

	cn4200NotificationEOC		NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
			"Embedded operations channel failure/cleared."
		::= { cn4200Notifications 5 }

	cn4200NotificationEQPT		NOTIFICATION-TYPE
		OBJECTS		{
			cn4200NotificationHelperPEOID, cn4200NotificationHelperPEType,
			cn4200NotificationHelperAction, cn4200NotificationHelperSev,
			cn4200NotificationDesc,
			cn4200NotificationHelperServiceIndicator,
			cn4200NotificationAffectedLP, cn4200NotificationAffectedSourceIP,
			cn4200NotificationHelperPEAID, cn4200NotificationHelperConfigChangeSeqNum
		}
		STATUS	current
		DESCRIPTION
			"Equipment failure/cleared."
		::= { cn4200Notifications 6 }

    cn4200NotificationEXTCONT		NOTIFICATION-TYPE
	    OBJECTS		{
		    cn4200NotificationHelperPEOID, cn4200NotificationHelperPEType,
			cn4200NotificationHelperAction, cn4200NotificationHelperSev,
			cn4200NotificationDesc, cn4200NotificationHelperPEAID
		}
		STATUS	current
		DESCRIPTION
		    "External condition activated."
		::= { cn4200Notifications 7 }

	cn4200NotificationFA		NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
			"Fuse alarm/cleared."
		::= { cn4200Notifications 8 }

	cn4200NotificationFACTERM		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Facility/circuit termination equipment failure/cleared."
		::= { cn4200Notifications 9 }

	cn4200NotificationFRCDWKSWPR		NOTIFICATION-TYPE
		OBJECTS		{
			cn4200NotificationHelperPEOID, cn4200NotificationHelperPEType,
			cn4200NotificationHelperAction, cn4200NotificationHelperSev,
			cn4200NotificationDesc, cn4200NotificationHelperPEAID,
            cn4200NotificationHelperStbyPEAID, cn4200NotificationHelperWrkPEAID,
			cn4200NotificationHelperConfigChangeSeqNum
		}
		STATUS	current
		DESCRIPTION
			"Forced working switch to protection/cleared."
		::= { cn4200Notifications 10 }

    cn4200NotificationFREEMEMLOW   NOTIFICATION-TYPE
	OBJECTS     {
		cn4200NotificationHelperPEOID, cn4200NotificationHelperPEType,
	    cn4200NotificationHelperAction, cn4200NotificationHelperSev,
	    cn4200NotificationDesc, cn4200NotificationHelperPEAID,
		cn4200NotificationHelperConfigChangeSeqNum
	}
	STATUS  current
	DESCRIPTION
	    "Free memory low."
	::= { cn4200Notifications 11 }

    cn4200NotificationFRNGSYNC     NOTIFICATION-TYPE
	OBJECTS     {
	    cn4200NotificationHelperPEOID, cn4200NotificationHelperPEType,
	    cn4200NotificationHelperAction, cn4200NotificationHelperSev,
	    cn4200NotificationDesc, cn4200NotificationAffectedLP, 
		cn4200NotificationAffectedSourceIP, cn4200NotificationHelperPEAID,
		cn4200NotificationHelperConfigChangeSeqNum
	}
	STATUS  current
	DESCRIPTION
	    "Free running synchronization mode/cleared."
	::= { cn4200Notifications 12 }

	cn4200NotificationHITEMP		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperConfigChangeSeqNum
		}
		STATUS	current
		DESCRIPTION
			"High temperature/cleared."
		::= { cn4200Notifications 13 }

	cn4200NotificationIMPROPMVL		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Improper removal/cleared."
		::= { cn4200Notifications 14 }

	cn4200NotificationINIT		NOTIFICATION-TYPE
		OBJECTS		{
			cn4200NotificationHelperPEOID, cn4200NotificationHelperPEType,
			cn4200NotificationHelperAction, cn4200NotificationHelperSev,
			cn4200NotificationDesc, cn4200NotificationInitLevel,
			cn4200NotificationHelperServiceIndicator,
			cn4200NotificationAffectedLP, cn4200NotificationAffectedSourceIP,
			cn4200NotificationHelperPEAID, cn4200NotificationHelperConfigChangeSeqNum
		}
		STATUS	current
		DESCRIPTION
			"Initialization level x will be executed."
		::= { cn4200Notifications 15 }

    cn4200NotificationLCK      NOTIFICATION-TYPE
	OBJECTS     {
	    cn4200NotificationHelperPEOID, cn4200NotificationHelperPEType,
	    cn4200NotificationHelperAction, cn4200NotificationHelperSev,
	    cn4200NotificationDesc, cn4200NotificationHelperServiceIndicator,
	    cn4200NotificationAffectedLP, cn4200NotificationAffectedSourceIP,
		cn4200NotificationHelperPEAID, cn4200NotificationHelperConfigChangeSeqNum
	}
	STATUS  current
	DESCRIPTION
	    "Channel administratively locked."
	::= { cn4200Notifications 16 }

    cn4200NotificationLOCKOUTOFPR      NOTIFICATION-TYPE
	OBJECTS     {
	    cn4200NotificationHelperPEOID, cn4200NotificationHelperPEType,
	    cn4200NotificationHelperAction, cn4200NotificationHelperSev,
	    cn4200NotificationDesc, cn4200NotificationHelperServiceIndicator,
	    cn4200NotificationAffectedLP, cn4200NotificationAffectedSourceIP,
		cn4200NotificationHelperPEAID, cn4200NotificationHelperConfigChangeSeqNum
	}
	STATUS  current
	DESCRIPTION
	    "Lockout of protection."
	::= { cn4200Notifications 17 }

	cn4200NotificationLOF		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Loss of frame/cleared."
		::= { cn4200Notifications 18 }

    cn4200NotificationLOGBUFROVFL  NOTIFICATION-TYPE
	OBJECTS     {
	    cn4200NotificationHelperPEType,
	    cn4200NotificationHelperAction, cn4200NotificationHelperSev,
	    cn4200NotificationDesc, cn4200NotificationLogName
	}
	STATUS  current
	DESCRIPTION
	    "Log buffer overflow."
	::= { cn4200Notifications 19 }

    cn4200NotificationLOGBUFRTH    NOTIFICATION-TYPE
	OBJECTS     {
	    cn4200NotificationHelperPEType,
	    cn4200NotificationHelperAction, cn4200NotificationHelperSev,
	    cn4200NotificationDesc, cn4200NotificationLogName
	}
	STATUS  current
	DESCRIPTION
	    "Log buffer usage above threshold."
	::= { cn4200Notifications 20 }

    cn4200NotificationLOM      NOTIFICATION-TYPE
	OBJECTS     {
	    cn4200NotificationHelperPEOID, cn4200NotificationHelperPEType,
	    cn4200NotificationHelperAction, cn4200NotificationHelperSev,
	    cn4200NotificationDesc, cn4200NotificationHelperServiceIndicator,
	    cn4200NotificationAffectedLP, cn4200NotificationAffectedSourceIP,
		cn4200NotificationHelperPEAID, cn4200NotificationHelperConfigChangeSeqNum
	}
	STATUS  current
	DESCRIPTION
	    "Loss of multiframe."
	::= { cn4200Notifications 21 }

    cn4200NotificationLOP      NOTIFICATION-TYPE
	OBJECTS     {
	    cn4200NotificationHelperPEOID, cn4200NotificationHelperPEType,
	    cn4200NotificationHelperAction, cn4200NotificationHelperSev,
	    cn4200NotificationDesc, cn4200NotificationHelperServiceIndicator,
	    cn4200NotificationAffectedLP, cn4200NotificationAffectedSourceIP,
		cn4200NotificationHelperPEAID, cn4200NotificationHelperConfigChangeSeqNum
	}
	STATUS  current
	DESCRIPTION
	    "Loss of pointer."
	::= { cn4200Notifications 22 }

	cn4200NotificationLOS		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Loss of signal/cleared."
		::= { cn4200Notifications 23 }

	cn4200NotificationLPBKFACILITY		NOTIFICATION-TYPE
		OBJECTS		{
			cn4200NotificationHelperPEOID, cn4200NotificationHelperPEType,
			cn4200NotificationHelperAction, cn4200NotificationHelperSev,
			cn4200NotificationDesc, cn4200NotificationAffectedLP, 
			cn4200NotificationAffectedSourceIP, cn4200NotificationHelperPEAID,
			cn4200NotificationHelperConfigChangeSeqNum
		}
		STATUS	current
		DESCRIPTION
			"Loop back, Facility/cleared."
		::= { cn4200Notifications 24 }

	cn4200NotificationLPBKTERM		NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
			"Loop back, Terminal/cleared."
		::= { cn4200Notifications 25 }

	cn4200NotificationMANWKSWPR		NOTIFICATION-TYPE
		OBJECTS		{
			cn4200NotificationHelperPEOID, cn4200NotificationHelperPEType,
			cn4200NotificationHelperAction, cn4200NotificationHelperSev,
			cn4200NotificationDesc, cn4200NotificationHelperPEAID,
            cn4200NotificationHelperStbyPEAID, cn4200NotificationHelperWrkPEAID,
			cn4200NotificationHelperConfigChangeSeqNum
		}
		STATUS	current
		DESCRIPTION
			"Manual switch to protection."
		::= { cn4200Notifications 26 }

    cn4200NotificationMISC		NOTIFICATION-TYPE
	    OBJECTS		{
		    cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
		    "Miscellaneous conditoin."
		::= { cn4200Notifications 27 }

    cn4200NotificationNDPLNK		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
			"NDP neighbor link cabling error."
		::= { cn4200Notifications 28 }

    cn4200NotificationNDPLNKUP    NOTIFICATION-TYPE
		OBJECTS		{
			gslamAGExternalConnectionLocalIP,
			gslamAGExternalConnectionLocalUMIC,
			cn4200NotificationHelperLocalPEType,
			cn4200NotificationHelperLocalPEOID,
			gslamAGExternalConnectionRemoteNodeIP,
			gslamAGExternalConnectionRemoteIP,
			gslamAGExternalConnectionRemoteUMIC,
			gslamAGExternalConnectionRemoteNodeType,
			gslamAGExternalConnectionLocalNodeTID,
			gslamAGExternalConnectionRemoteNodeTID,
			cn4200NotificationDesc,
			cn4200NotificationHelperLocalPEAID,
			cn4200NotificationHelperRemotePEAID,
			gslamAGExternalConnectionRemotePortAID
		}
		STATUS	current
		DESCRIPTION
		    "Neighbor link up."
		::= { cn4200Notifications 29 }

    cn4200NotificationNDPLNKDN	NOTIFICATION-TYPE
		OBJECTS		{
			gslamAGExternalConnectionLocalIP,
			gslamAGExternalConnectionLocalUMIC,
			cn4200NotificationHelperLocalPEType,
			cn4200NotificationHelperLocalPEOID,
			gslamAGExternalConnectionRemoteNodeIP,
			gslamAGExternalConnectionRemoteIP,
			gslamAGExternalConnectionRemoteUMIC,
			gslamAGExternalConnectionRemoteNodeType,
			gslamAGExternalConnectionLocalNodeTID,
			gslamAGExternalConnectionRemoteNodeTID,
			cn4200NotificationDesc,
			cn4200NotificationHelperLocalPEAID,
			cn4200NotificationHelperRemotePEAID,
			gslamAGExternalConnectionRemotePortAID
		}
		STATUS	current
		DESCRIPTION
		    "Neighbor link down."
		::= { cn4200Notifications 30 }

    cn4200NotificationNDP	NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
			"NDP neighbor discovery misconfiguration."
		::= { cn4200Notifications 31 }

    cn4200NotificationNTPSYNC  NOTIFICATION-TYPE
	OBJECTS     {
	    cn4200NotificationHelperPEType,
	    cn4200NotificationHelperAction, cn4200NotificationHelperSev,
	    cn4200NotificationDesc
	}
	STATUS  current
	DESCRIPTION
	    "NTP synchronization failure."
	::= { cn4200Notifications 32 }

	cn4200NotificationOCI		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Open matrix connection defect/cleared."
		::= { cn4200Notifications 33 }

	cn4200NotificationOSLINK		NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
			"Management Link has failed/recovered."
		::= { cn4200Notifications 34 }

	cn4200NotificationPDI		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Payload defect indication/cleared."
		::= { cn4200Notifications 35 }

	cn4200NotificationPLM		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Payload label mismatch for path."
		::= { cn4200Notifications 36 }

	cn4200NotificationPRCDRERR		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Procedure error, mismatch of attributes/cleared."
		::= { cn4200Notifications 37 }

	cn4200NotificationPWRRESTART		NOTIFICATION-TYPE
		OBJECTS		{
			cn4200NotificationHelperPEOID, cn4200NotificationHelperPEType,
			cn4200NotificationHelperAction, cn4200NotificationHelperSev,
			cn4200NotificationDesc, cn4200NotificationAffectedLP, 
			cn4200NotificationAffectedSourceIP, cn4200NotificationHelperPEAID
		}
		STATUS	current
		DESCRIPTION
			"Power fail restart."
		::= { cn4200Notifications 38 }

	cn4200NotificationRFI		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
			"Remote failure indication/cleared."
		::= { cn4200Notifications 39 }

	cn4200NotificationROLL		NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
			"Roll in progress/cleared."
		::= { cn4200Notifications 40 }

    cn4200NotificationSDBER	NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID
		}
		STATUS	current
		DESCRIPTION
			"Signal degrade due to BER."
		::= { cn4200Notifications 41 }

    cn4200NotificationSFBER		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID
		}
		STATUS	current
		DESCRIPTION
			"Signal failure due to BER."
		::= { cn4200Notifications 42 }

 	cn4200NotificationSFT		NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
			"Software or operating system/cleared."
		::= { cn4200Notifications 43 }

	cn4200NotificationSFTWDN		NOTIFICATION-TYPE
		OBJECTS		{
			cn4200NotificationHelperPEType,
			cn4200NotificationHelperAction, cn4200NotificationHelperSev,
			cn4200NotificationDesc
		}
		STATUS	current
		DESCRIPTION
			"Software download in progress/cleared."
		::= { cn4200Notifications 44 }

    cn4200NotificationSYNC     NOTIFICATION-TYPE
	OBJECTS     {
	    cn4200NotificationHelperPEOID, cn4200NotificationHelperPEType,
	    cn4200NotificationHelperAction, cn4200NotificationHelperSev,
	    cn4200NotificationDesc, cn4200NotificationAffectedLP, 
		cn4200NotificationAffectedSourceIP, cn4200NotificationHelperPEAID,
		cn4200NotificationHelperConfigChangeSeqNum
	}
	STATUS  current
	DESCRIPTION
	    "Loss of timing on synchronization link/cleared."
	::= { cn4200Notifications 45 }

	cn4200NotificationTHSHVLT		NOTIFICATION-TYPE
		OBJECTS		{
			cn4200NotificationHelperPEOID, cn4200NotificationHelperPEType,
			cn4200NotificationHelperAction, cn4200NotificationHelperSev,
			cn4200NotificationDesc, cn4200NotificationMonTypeAndDir,
			cn4200NotificationHelperMonValue, cn4200NotificationHelperMonThreshold,
			cn4200NotificationHelperPEAID
		}
		STATUS	current
		DESCRIPTION
			"Threshold violation."
		::= { cn4200Notifications 46 }

	cn4200NotificationTIM		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Trace identifier message defect/cleared."
		::= { cn4200Notifications 47 }

	cn4200NotificationREBOOTED		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID
		}
		STATUS	current
		DESCRIPTION
			"Reboot completed."
		::= { cn4200Notifications 48 }

	cn4200NotificationWKSWPR		NOTIFICATION-TYPE
		OBJECTS		{
			cn4200NotificationHelperPEOID, cn4200NotificationHelperPEType,
			cn4200NotificationHelperAction, cn4200NotificationHelperSev,
			cn4200NotificationDesc, cn4200NotificationHelperPEAID,
            cn4200NotificationHelperStbyPEAID, cn4200NotificationHelperWrkPEAID,
			cn4200NotificationHelperConfigChangeSeqNum
		}
		STATUS	current
		DESCRIPTION
			"Protection switch event."
		::= { cn4200Notifications 49 }

   	cn4200NotificationWTR		NOTIFICATION-TYPE
       	OBJECTS		{
	    cn4200NotificationHelperPEOID, cn4200NotificationHelperPEType,
	    cn4200NotificationHelperAction, cn4200NotificationHelperSev,
	    cn4200NotificationDesc, cn4200NotificationHelperPEAID
	}
	STATUS	current
	DESCRIPTION
	    "Wait-to-Restore Interval."
	::= { cn4200Notifications 50 }

    cn4200NotificationACO		NOTIFICATION-TYPE
	    OBJECTS		{
		    cn4200NotificationHelperPEType,
			cn4200NotificationHelperAction, cn4200NotificationHelperSev,
			cn4200NotificationDesc
		}
		STATUS	current
		DESCRIPTION
		    "Alarm cutoff active."
		::= { cn4200Notifications 51 }

    cn4200NotificationUPM		NOTIFICATION-TYPE
	    OBJECTS		{
		    cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID
		}
		STATUS	current
		DESCRIPTION
		    "User payload mismatch."
		::= { cn4200Notifications 52 }

    cn4200NotificationAUTORESTART		NOTIFICATION-TYPE
		OBJECTS		{
			cn4200NotificationHelperPEOID, cn4200NotificationHelperPEType,
			cn4200NotificationHelperAction, cn4200NotificationHelperSev,
			cn4200NotificationDesc, cn4200NotificationAffectedLP, 
			cn4200NotificationAffectedSourceIP, cn4200NotificationHelperPEAID
		}
		STATUS	current
		DESCRIPTION
			"Automatic Reset"
		::= { cn4200Notifications 53 }

     cn4200NotificationDEG		NOTIFICATION-TYPE
		OBJECTS		{
			cn4200NotificationHelperPEOID, cn4200NotificationHelperPEType,
			cn4200NotificationHelperAction, cn4200NotificationDesc,
			cn4200NotificationHelperServiceIndicator,
			cn4200NotificationAffectedLP, cn4200NotificationAffectedSourceIP,
			cn4200NotificationHelperPEAID
		}
		STATUS	current
		DESCRIPTION
			"Signal Degrade."
		::= { cn4200Notifications 54 }

     cn4200NotificationINHMSG		NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
			"Autonomous messages inhibited."
		::= { cn4200Notifications 55 }

     cn4200NotificationINTRUSION		NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
			"Intrusion Attempt Suspected."
		::= { cn4200Notifications 56 }

     cn4200NotificationRELMIG		NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
			"Release Migration."
		::= { cn4200Notifications 57 }

     cn4200NotificationTUIDAGE		NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
			"User Account Inactivity Timeout."
		::= { cn4200Notifications 58 }

	cn4200NotificationCFGERR		NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
			"Configuration Error. Eg: Mismatch of power mod type during
			multi single board configuration."
		::= { cn4200Notifications 59 }

	cn4200NotificationPWRLOADBAL		NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
			"Power module load balance error."
		::= { cn4200Notifications 60 }

	cn4200NotificationPWR		NOTIFICATION-TYPE
		OBJECTS		{
			cn4200NotificationHelperPEOID, cn4200NotificationHelperPEType,
			cn4200NotificationHelperAction, cn4200NotificationHelperSev,
			cn4200NotificationDesc, cn4200NotificationAffectedLP, 
			cn4200NotificationAffectedSourceIP, cn4200NotificationHelperPEAID
		}
		STATUS	current
		DESCRIPTION
			"Voltage threshold on power module."
		::= { cn4200Notifications 61 }

	cn4200NotificationLOWTEMP		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperConfigChangeSeqNum
		}
		STATUS	current
		DESCRIPTION
			"Low temperature/cleared."
		::= { cn4200Notifications 62 }

	cn4200NotificationEXM		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID
		}
		STATUS	current
		DESCRIPTION
			"Extension header mismatch."
		::= { cn4200Notifications 63 }

        cn4200NotificationDATAFLT		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Unable to program firmware"
		::= { cn4200Notifications 64 }

        cn4200NotificationINTMSGERR		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID
		}
		STATUS	current
		DESCRIPTION
			"Internal message error."
		::= { cn4200Notifications 65 }

	cn4200NotificationLFD		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Loss of frame delineation."
		::= { cn4200Notifications 66 }

	cn4200NotificationALMCKT	NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
			"Alarm circuit failure."
		::= { cn4200Notifications 67 }

	cn4200NotificationFEED	NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
			"Dual power feed detected."
		::= { cn4200Notifications 68 }

	cn4200NotificationTIMPS	NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
			"Timing source protection switch."
		::= { cn4200Notifications 69 }

	cn4200NotificationSYNCPRI     NOTIFICATION-TYPE
		OBJECTS     {
	    		cn4200NotificationHelperPEOID, cn4200NotificationHelperPEType,
	    		cn4200NotificationHelperAction, cn4200NotificationHelperSev,
	    		cn4200NotificationDesc, cn4200NotificationAffectedLP, 
				cn4200NotificationAffectedSourceIP, cn4200NotificationHelperPEAID,
				cn4200NotificationHelperConfigChangeSeqNum
		}
		STATUS  current
		DESCRIPTION
	    		"Loss of timing on primary synchronization link."
		::= { cn4200Notifications 70 }

	cn4200NotificationSYNCSEC     NOTIFICATION-TYPE
		OBJECTS     {
	    		cn4200NotificationHelperPEOID, cn4200NotificationHelperPEType,
	    		cn4200NotificationHelperAction, cn4200NotificationHelperSev,
	    		cn4200NotificationDesc, cn4200NotificationAffectedLP, 
				cn4200NotificationAffectedSourceIP, cn4200NotificationHelperPEAID,
				cn4200NotificationHelperConfigChangeSeqNum
		}
		STATUS  current
		DESCRIPTION
	    		"Loss of timing on secondary synchronization link."
		::= { cn4200Notifications 71 }

	cn4200NotificationDCMFAIL		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"DCM Connection Failure."
		::= { cn4200Notifications 72 }

	cn4200NotificationOPTPWRCNTRL		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Optical power level control failure."
		::= { cn4200Notifications 73 }

	cn4200NotificationTECCURRENT		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"High laser TEC current."
		::= { cn4200Notifications 74 }

	cn4200NotificationPUMPCURRENT		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"High Laser Pump Current."
		::= { cn4200Notifications 75 }

	cn4200NotificationLOFO		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperConfigChangeSeqNum
		}
		STATUS	current
		DESCRIPTION
			"Loss of frame, OSC."
		::= { cn4200Notifications 76 }

	cn4200NotificationLOSO		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperConfigChangeSeqNum
		}
		STATUS	current
		DESCRIPTION
			"Loss of Signal, OSC."
		::= { cn4200Notifications 77 }

	cn4200NotificationLOSP		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"Loss of Signal, Payload."
		::= { cn4200Notifications 78 }

	cn4200NotificationREMOTEFLT		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
			"Remote fault ordered set."
		::= { cn4200Notifications 79 }

	cn4200NotificationSYNCOOS     NOTIFICATION-TYPE
		OBJECTS     {
	    		cn4200NotificationHelperPEOID, cn4200NotificationHelperPEType,
	    		cn4200NotificationHelperAction, cn4200NotificationHelperSev,
	    		cn4200NotificationDesc, cn4200NotificationAffectedLP, 
				cn4200NotificationAffectedSourceIP, cn4200NotificationHelperPEAID
		}
		STATUS  current
		DESCRIPTION
	    		"Loss of timing on both Primary & secondary synchronization links"
		::= { cn4200Notifications 80 }

	cn4200NotificationASDDISABLED     NOTIFICATION-TYPE
		OBJECTS     {
	    		cn4200NotificationHelperPEOID, cn4200NotificationHelperPEType,
	    		cn4200NotificationHelperAction, cn4200NotificationHelperSev,
	    		cn4200NotificationDesc, cn4200NotificationHelperPEAID
		}
		STATUS  current
		DESCRIPTION
	    		"Auto-laser shutdown disabled"
		::= { cn4200Notifications 81 }

	cn4200NotificationSWTOPRI	NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
				"Synchronization switch to primary clock"
		::= { cn4200Notifications 82 }

	cn4200NotificationSWTOSEC	NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
				"Synchronization switch to secondary clock"
		::= { cn4200Notifications 83 }

	cn4200NotificationFRCDSWTOPRI	NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
				"Forced synchronization switch to primary clock"
		::= { cn4200Notifications 84 }

	cn4200NotificationFRCDSWTOSEC	NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
				"Forced synchronization switch to primary clock"
		::= { cn4200Notifications 85 }

	cn4200NotificationSWTOINT	NOTIFICATION-TYPE
		OBJECTS		{
			cn4200NotificationHelperPEOID, cn4200NotificationHelperPEType,
			cn4200NotificationHelperAction, cn4200NotificationHelperSev,
			cn4200NotificationDesc, cn4200NotificationHelperPEAID
		}
		STATUS	current
		DESCRIPTION
				"Synchronization switch to internal clock"
		::= { cn4200Notifications 86 }

	cn4200NotificationGLOCS	NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
				"GFP Loss of Client Signal"
		::= { cn4200Notifications 87 }

	cn4200NotificationGRDI	NOTIFICATION-TYPE
		OBJECTS		{
			cn4200NotificationHelperPEOID, cn4200NotificationHelperPEType,
			cn4200NotificationHelperAction, cn4200NotificationHelperSev,
			cn4200NotificationDesc, cn4200NotificationHelperPEAID,
			cn4200NotificationHelperConfigChangeSeqNum
		}
		STATUS	current
		DESCRIPTION
				"GFP Remote Defect Indication"
		::= { cn4200Notifications 88 }

	cn4200NotificationLOCALFLT		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperConfigChangeSeqNum
		}
		STATUS	current
		DESCRIPTION
			"Local fault ordered set."
		::= { cn4200Notifications 89 }

	cn4200NotificationSVCERR		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperConfigChangeSeqNum
		}
		STATUS	current
		DESCRIPTION
			"Service Class Error."
		::= { cn4200Notifications 90 }

	cn4200NotificationAISL		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperConfigChangeSeqNum
		}
		STATUS	current
		DESCRIPTION
			"Line Alarm Indication Signal detected"
		::= { cn4200Notifications 91 }

	cn4200NotificationLCLACCESS	NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
			"Local Mgmt Access Enabled"
		::= { cn4200Notifications 92 }

	-- *******************R5.0****************************
    cn4200NotificationNDPLINKUP    NOTIFICATION-TYPE
        OBJECTS     {
            gslamAGREL50ExtCXLocalIP,
            gslamAGREL50ExtCXLocalShelf,
			gslamAGREL50ExtCXLocalMod,
			gslamAGREL50ExtCXLocalPort,
            cn4200NotificationHelperLocalPEType,
            cn4200NotificationHelperLocalPEOID,
            gslamAGREL50ExtCXRemoteNodeIP,
            gslamAGREL50ExtCXRemoteIP,
            gslamAGREL50ExtCXRemoteShelf,
			gslamAGREL50ExtCXRemoteMod,
			gslamAGREL50ExtCXRemotePort,
            gslamAGREL50ExtCXRemoteNodeType,
            gslamAGREL50ExtCXLocalNodeTID,
            gslamAGREL50ExtCXRemoteNodeTID,
            cn4200NotificationDesc,
            cn4200NotificationHelperLocalPEAID,
            cn4200NotificationHelperRemotePEAID,
            cn4200NotificationHelperAlarmType,
            gslamAGREL50ExtCXRemotePortAID
        }
        STATUS  current
        DESCRIPTION
            "Neighbor link up."
        ::= { cn4200Notifications 93 }

    cn4200NotificationNDPLINKDN  NOTIFICATION-TYPE
        OBJECTS     {
			gslamAGREL50ExtCXLocalIP,
            gslamAGREL50ExtCXLocalShelf,
            gslamAGREL50ExtCXLocalMod,
            gslamAGREL50ExtCXLocalPort,
            cn4200NotificationHelperLocalPEType,
            cn4200NotificationHelperLocalPEOID,
            gslamAGREL50ExtCXRemoteNodeIP,
            gslamAGREL50ExtCXRemoteIP,
            gslamAGREL50ExtCXRemoteShelf,
            gslamAGREL50ExtCXRemoteMod,
            gslamAGREL50ExtCXRemotePort,
            gslamAGREL50ExtCXRemoteNodeType,
            gslamAGREL50ExtCXLocalNodeTID,
            gslamAGREL50ExtCXRemoteNodeTID,
            cn4200NotificationDesc,
            cn4200NotificationHelperLocalPEAID,
            cn4200NotificationHelperRemotePEAID,
            cn4200NotificationHelperAlarmType,
            gslamAGREL50ExtCXRemotePortAID
        }
        STATUS  current
        DESCRIPTION
            "Neighbor link down."
        ::= { cn4200Notifications 94 }

	cn4200NotificationSHELFLOWVOLT	NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperAlarmType
		}
		STATUS	current
		DESCRIPTION
			"LowVoltage Alarm against UV SHELF (ROADM_SH)"
		::= { cn4200Notifications 95 }

	cn4200NotificationSHELFPWRALARM		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperAlarmType
		}
		STATUS	current
		DESCRIPTION
			"PWR Alarm against UV SHELF (ROADM_SH)"
		::= { cn4200Notifications 96 }

	cn4200NotificationPDUFEEDBATTERY	NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperAlarmType
		}
		STATUS	current
		DESCRIPTION
			"pdu Feed Battery Alarm (ROADM_SH)"
		::= { cn4200Notifications 97 }

	cn4200NotificationPDUFUSEBATTERY	NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperAlarmType
		}
		STATUS	current
		DESCRIPTION
			"pdu Fuse Battery Alarm (ROADM_SH)"
		::= { cn4200Notifications 98 }

	cn4200NotificationUVCTRLRPWR	NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperAlarmType
		}
		STATUS	current
		DESCRIPTION
			"UV Controller Power (ROADM_SH)"
		::= { cn4200Notifications 99 }

	cn4200NotificationIOMPWR	NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperAlarmType
		}
		STATUS	current
		DESCRIPTION
			"R5 Form Factor Power Alarm (ROADM_SH)"
		::= { cn4200Notifications 100 }

	cn4200NotificationFANFAILURE	NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID, cn4200NotificationHelperAlarmType
		}
		STATUS	current
		DESCRIPTION
			"Fan Failure alarm (ROADM_SH)"
		::= { cn4200Notifications 101 }

    cn4200NotificationSWOFRCDPRI     NOTIFICATION-TYPE
	OBJECTS     {
	    cn4200NotificationHelperPEOID, cn4200NotificationHelperPEType,
	    cn4200NotificationHelperAction, cn4200NotificationHelperSev,
	    cn4200NotificationDesc, cn4200NotificationAffectedLP, 
		cn4200NotificationAffectedSourceIP, cn4200NotificationHelperPEAID,
        cn4200NotificationHelperAlarmType
	}
	STATUS  current
	DESCRIPTION
	    "switchover forced to primary"
	::= { cn4200Notifications 102 }

    cn4200NotificationSWOFRCDSEC     NOTIFICATION-TYPE
	OBJECTS     {
	    cn4200NotificationHelperPEOID, cn4200NotificationHelperPEType,
	    cn4200NotificationHelperAction, cn4200NotificationHelperSev,
	    cn4200NotificationDesc, cn4200NotificationAffectedLP, 
		cn4200NotificationAffectedSourceIP, cn4200NotificationHelperPEAID,
        cn4200NotificationHelperAlarmType
	}
	STATUS  current
	DESCRIPTION
	    "switchover forced to secondary"
	::= { cn4200Notifications 103 }

        cn4200NotificationDATAERR       NOTIFICATION-TYPE
                OBJECTS         {
                        cn4200NotificationHelperPEOID, cn4200NotificationHelperPEType,
                        cn4200NotificationHelperAction, cn4200NotificationHelperSev,
                        cn4200NotificationDesc, cn4200NotificationHelperServiceIndicator,
                        cn4200NotificationHelperPEAID, cn4200NotificationHelperAlarmType
                }
                STATUS  current
                DESCRIPTION
                        "Database integrity error"
                ::= { cn4200Notifications 104 }

        cn4200NotificationBKUPMEMT      NOTIFICATION-TYPE
                OBJECTS         {
                        cn4200NotificationHelperPEOID, cn4200NotificationHelperPEType,
                        cn4200NotificationHelperAction, cn4200NotificationHelperSev,
                        cn4200NotificationDesc, cn4200NotificationHelperServiceIndicator,
                        cn4200NotificationHelperPEAID
                }
                STATUS  current
                DESCRIPTION
                        "Top NV Backup Memory failure"
                ::= { cn4200Notifications 105 }

        cn4200NotificationBKUPMEMB      NOTIFICATION-TYPE
                OBJECTS         {
                        cn4200NotificationHelperPEOID, cn4200NotificationHelperPEType,
                        cn4200NotificationHelperAction, cn4200NotificationHelperSev,
                        cn4200NotificationDesc, cn4200NotificationHelperServiceIndicator,
                        cn4200NotificationHelperPEAID
                }
                STATUS  current
                DESCRIPTION
                        "Bottom NV Backup Memory failure"
                ::= { cn4200Notifications 106 }

        cn4200NotificationBKUPMEMNA     NOTIFICATION-TYPE
                OBJECTS         {
                        cn4200NotificationHelperPEOID, cn4200NotificationHelperPEType,
                        cn4200NotificationHelperAction, cn4200NotificationHelperSev,
                        cn4200NotificationDesc, cn4200NotificationHelperServiceIndicator,
                        cn4200NotificationHelperPEAID
                }
                STATUS  current
                DESCRIPTION
                        "Bottom NV Backup Memory not available"
                ::= { cn4200Notifications 107 }

	-- MSDca74992 (Sep-11/07)
	cn4200NotificationTRMT		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
			"We are not going to raise a module failure alarm 
				against the DWR module on detecting LoS in the 
				Transmit direction 
				2.  We are instead going to report a TRMT -ie 
					Transmitter Failure - alarm against the appropriate 
					port for the DWR. 
				2a. On Master DWRs, it will be against the unidirectional 
					OCG NTWK-OUT port 
				2b. On Slave DWRs, it will be against the bidirectional 
					OCG NTWK port"
		::= { cn4200Notifications 108 }

	-- MSDca75349
	cn4200NotificationBDI		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
			"Backward Defect Indication indication/cleared."
		::= { cn4200Notifications 109 }

	-- MSDca75452 (Notifications 110 - 113)
	cn4200NotificationFDI		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
			"Forward defect Indication indication/cleared."
		::= { cn4200Notifications 110 }

	cn4200NotificationPMI		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
			"Payload missing indication indication/cleared."
		::= { cn4200Notifications 111 }

	cn4200NotificationOCMFAIL		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
			"OCM measurement fail indication/cleared."
		::= { cn4200Notifications 112 }

	cn4200NotificationOVERLOAD		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationHelperPEAID
		}
		STATUS	current
		DESCRIPTION
			"OSC Receiver overload indication/cleared."
		::= { cn4200Notifications 113 }

    -- Device Authentication related traps
    cn4200NotificationDevAuthFailure      NOTIFICATION-TYPE
        OBJECTS     {
            cn4200NotificationHelperPEOID, cn4200NotificationHelperPEType,
            cn4200NotificationHelperAction, cn4200NotificationHelperSev,
            cn4200NotificationDesc, cn4200NotificationHelperServiceIndicator,
            cn4200NotificationHelperPEAID, cn4200NotificationHelperAlarmType
        }
        STATUS  current
        DESCRIPTION
            "Device Authentication Failure alarm indication/cleared."
        ::= { cn4200Notifications 114 }

    cn4200NotificationDevAuthProtocolErr      NOTIFICATION-TYPE
        OBJECTS     {
            cn4200NotificationHelperPEOID, cn4200NotificationHelperPEType,
            cn4200NotificationHelperAction, cn4200NotificationHelperSev,
            cn4200NotificationDesc, cn4200NotificationHelperServiceIndicator,
            cn4200NotificationHelperPEAID, cn4200NotificationHelperAlarmType
        }
        STATUS  current
        DESCRIPTION
            "Device Authentication Protocol Error alarm indication/cleared."
        ::= { cn4200Notifications 115 }

    cn4200NotificationDevAuthProtocolVer      NOTIFICATION-TYPE
        OBJECTS     {
            cn4200NotificationHelperPEOID, cn4200NotificationHelperPEType,
            cn4200NotificationHelperAction, cn4200NotificationHelperSev,
            cn4200NotificationDesc, cn4200NotificationHelperServiceIndicator,
            cn4200NotificationHelperPEAID, cn4200NotificationHelperAlarmType
        }
        STATUS  current
        DESCRIPTION
            "Device Authentication Protocol Version alarm indication/cleared."
        ::= { cn4200Notifications 116 }

    cn4200NotificationDevAuthProtocolVerChg      NOTIFICATION-TYPE
        OBJECTS     {
            cn4200NotificationHelperPEOID, cn4200NotificationHelperPEType,
            cn4200NotificationHelperAction, cn4200NotificationHelperSev,
            cn4200NotificationDesc,
            cn4200NotificationHelperPEAID,
            cn4200NotificationHelperAlarmType
        }
        STATUS  current
        DESCRIPTION
            "Device Authentication Protocol Version Change event indication."
        ::= { cn4200Notifications 117 }

    cn4200NotificationAPSDDisabled      NOTIFICATION-TYPE
        OBJECTS     {
            cn4200NotificationHelperPEOID, cn4200NotificationHelperPEType,
            cn4200NotificationHelperAction, cn4200NotificationHelperSev,
            cn4200NotificationDesc, 
            cn4200NotificationHelperPEAID 
        }
        STATUS  current
        DESCRIPTION
            "APSD Disabled event indication."
        ::= { cn4200Notifications 118 }

    cn4200NotificationAPSDNA      NOTIFICATION-TYPE
        OBJECTS     {
            cn4200NotificationHelperPEOID, cn4200NotificationHelperPEType,
            cn4200NotificationHelperAction, cn4200NotificationHelperSev,
            cn4200NotificationDesc, 
            cn4200NotificationHelperPEAID 
        }
        STATUS  current
        DESCRIPTION
            "APSD Not Available event indication."
        ::= { cn4200Notifications 119 }

    cn4200NotificationDCMEXCSSLOSS      NOTIFICATION-TYPE
        OBJECTS     {
            cn4200NotificationHelperPEOID, cn4200NotificationHelperPEType,
            cn4200NotificationHelperAction, cn4200NotificationHelperSev,
            cn4200NotificationDesc,
            cn4200NotificationHelperPEAID
        }
        STATUS  current
        DESCRIPTION
            "DCM Excessive Loss alarm indication."
        ::= { cn4200Notifications 120 }

    cn4200NotificationOAOVERLOAD     NOTIFICATION-TYPE
        OBJECTS     {
            cn4200NotificationHelperPEOID, cn4200NotificationHelperPEType,
            cn4200NotificationHelperAction, cn4200NotificationHelperSev,
            cn4200NotificationDesc,
            cn4200NotificationHelperPEAID
        }
        STATUS  current
        DESCRIPTION
            "OA Overlaod alarm indication."
        ::= { cn4200Notifications 121 }

    cn4200NotificationRLOS      NOTIFICATION-TYPE
        OBJECTS     {
            cn4200NotificationHelperPEOID, cn4200NotificationHelperPEType,
            cn4200NotificationHelperAction, cn4200NotificationHelperSev,
            cn4200NotificationDesc,
            cn4200NotificationHelperPEAID
        }
        STATUS  current
        DESCRIPTION
            "RLOS event/alarm indication."
        ::= { cn4200Notifications 122 }

    cn4200NotificationLPBKCRS      NOTIFICATION-TYPE
        OBJECTS     {
            cn4200NotificationHelperPEOID, cn4200NotificationHelperPEType,
            cn4200NotificationHelperAction, cn4200NotificationHelperSev,
            cn4200NotificationDesc, cn4200NotificationHelperPEAID
        }
        STATUS  current
        DESCRIPTION
            "Loop back, CRS/cleared."
        ::= { cn4200Notifications 123 }

    cn4200NotificationPROGFLT      NOTIFICATION-TYPE
        OBJECTS     {
            cn4200NotificationHelperPEOID, cn4200NotificationHelperPEType,
            cn4200NotificationHelperAction, cn4200NotificationHelperSev,
            cn4200NotificationDesc,
            cn4200NotificationHelperPEAID
        }
        STATUS  current
        DESCRIPTION
            "PROGRAM FAULT alarm indication."
        ::= { cn4200Notifications 124 }

-- ***** ESOM SUPPORT STARTS *****
	cn4200NotificationOOF	NOTIFICATION-TYPE
	OBJECTS     {
		cn4200NotificationHelperPEOID, cn4200NotificationHelperPEType,
		cn4200NotificationHelperAction, cn4200NotificationHelperSev,
		cn4200NotificationDesc, cn4200NotificationHelperServiceIndicator,
		cn4200NotificationAffectedLP, cn4200NotificationAffectedSourceIP,
		cn4200NotificationHelperPEAID
		}
		STATUS  current
		DESCRIPTION
		    "Out of frame"
	::= { cn4200Notifications 125 }
	
	cn4200NotificationUNEQ	NOTIFICATION-TYPE
	OBJECTS     {
		cn4200NotificationHelperPEOID, cn4200NotificationHelperPEType,
		cn4200NotificationHelperAction, cn4200NotificationHelperSev,
		cn4200NotificationDesc, cn4200NotificationHelperServiceIndicator,
		cn4200NotificationAffectedLP, cn4200NotificationAffectedSourceIP,
		cn4200NotificationHelperPEAID
		}
		STATUS  current
		DESCRIPTION
		    "Payload Unequiped"
	::= { cn4200Notifications 126 }
	
	cn4200NotificationLINKINPROG	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Link Initialization In Progress"
	::= { cn4200Notifications 127 }
	
	cn4200NotificationSNEGINPROG	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Speed Negotiation In Progress"
	::= { cn4200Notifications 128 }
	
	cn4200NotificationCRDDETFAIL	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Credit Detection Failure"
	::= { cn4200Notifications 129 }
	
	cn4200NotificationANEGINPROG	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Autonegotiation In Progress"
	::= { cn4200Notifications 130 }
	
	cn4200NotificationANEGLKERR	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Autonegotiation Link Error"
	::= { cn4200Notifications 131 }
	
	cn4200NotificationANEGLKFAIL	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Autonegotiation Link Fail"
	::= { cn4200Notifications 132 }
	
	cn4200NotificationANEGLKOFFL	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Autonegotiation Link Offline"
	::= { cn4200Notifications 133 }
	
	cn4200NotificationANEGMISM	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Autonegotiation Mismatch"
	::= { cn4200Notifications 134 }
	
	cn4200NotificationATTRMISM	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Datapath Attribute Mismatch"
	::= { cn4200Notifications 135 }
	
	cn4200NotificationRXCONTFLT	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Receive Continuity Fault"
	::= { cn4200Notifications 136 }
	
	cn4200NotificationTXCONTFLT	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Transmit Continuity Fault"
	::= { cn4200Notifications 137 }
	
	cn4200NotificationFLTNOTIFY	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Fault Notification in Effect"
	::= { cn4200Notifications 138 }
	
	cn4200NotificationZEROBWASGN	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Zero Bandwidth Assigned"
	::= { cn4200Notifications 139 }
	
	cn4200NotificationPROTCHM	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Protection Channel Mismatch"
	::= { cn4200Notifications 140 }
	
	cn4200NotificationPSWNOTIFY	NOTIFICATION-TYPE
	OBJECTS     {
		cn4200NotificationHelperPEOID, cn4200NotificationHelperPEType,
		cn4200NotificationHelperAction, cn4200NotificationHelperSev,
		cn4200NotificationDesc, cn4200NotificationHelperPEAID
		}
		STATUS  current
		DESCRIPTION
		    "Protection Switch Notification in Effect"
	::= { cn4200Notifications 141 }
        cn4200NotificationHIREFLCTLOSS     NOTIFICATION-TYPE
        OBJECTS     {
                cn4200NotificationHelperPEOID, cn4200NotificationHelperPEType,
                cn4200NotificationHelperAction, cn4200NotificationHelperSev,
                cn4200NotificationDesc, cn4200NotificationHelperServiceIndicator,
                cn4200NotificationHelperPEAID
                }
                STATUS  current
                DESCRIPTION
                    "High reflection loss detected by the RAMAN amplifier"
        ::= { cn4200Notifications 142 }

	-- ***** ESOM SUPPORT ENDS *****

        cn4200NotificationMANRESTART     NOTIFICATION-TYPE
        OBJECTS     {
                cn4200NotificationHelperPEOID, cn4200NotificationHelperPEType,
                cn4200NotificationHelperAction, cn4200NotificationHelperSev,
                cn4200NotificationDesc, cn4200NotificationHelperServiceIndicator,
                cn4200NotificationHelperPEAID
                }
                STATUS  current
                DESCRIPTION
                    "Manual Restart"
        ::= { cn4200Notifications 143 }

	-- OSPF Traps

	-- Standard mib Traps

    cn4200OSPFVirtIfStateChange NOTIFICATION-TYPE
        OBJECTS {
                    ospfRouterId, -- The originator of the trap
                    ospfVirtIfAreaId,
                    ospfVirtIfNeighbor,
                    ospfVirtIfState  -- The new state
                  }
        STATUS             current
        DESCRIPTION
           "An ospfIfStateChange trap signifies that there
           has  been a change in the state of an OSPF vir-
           tual interface.
           This trap should be generated when  the  inter-
           face  state  regresses  (e.g., goes from Point-
           to-Point to Down) or progresses to  a  terminal
           state (i.e., Point-to-Point)."
   ::= { cn4200Notifications 145 }


    cn4200OSPFNbrStateChange NOTIFICATION-TYPE
        OBJECTS {
                    ospfRouterId, -- The originator of the trap
                    ospfNbrIpAddr,
                    ospfNbrAddressLessIndex,
                    ospfNbrRtrId,
                    ospfNbrState  -- The new state
                  }
        STATUS             current
        DESCRIPTION
           "An  ospfNbrStateChange  trap  signifies   that
           there  has been a change in the state of a non-
           virtual OSPF neighbor.   This  trap  should  be
           generated  when  the  neighbor  state regresses
           (e.g., goes from Attempt or Full  to  1-Way  or
           Down)  or progresses to a terminal state (e.g.,
           2-Way or Full).  When an  neighbor  transitions
           from  or  to Full on non-broadcast multi-access
           and broadcast networks, the trap should be gen-
           erated  by the designated router.  A designated
           router transitioning to Down will be  noted  by
           ospfIfStateChange."
   ::= { cn4200Notifications 146 }


    cn4200OSPFVirtNbrStateChange NOTIFICATION-TYPE
        OBJECTS {
                    ospfRouterId, -- The originator of the trap
                    ospfVirtNbrArea,
                    ospfVirtNbrRtrId,
                    ospfVirtNbrState  -- The new state
                  }
        STATUS             current
        DESCRIPTION
           "An ospfIfStateChange trap signifies that there
           has  been a change in the state of an OSPF vir-
           tual neighbor.  This trap should  be  generated
           when  the  neighbor state regresses (e.g., goes
           from Attempt or  Full  to  1-Way  or  Down)  or
           progresses to a terminal state (e.g., Full)."
   ::= { cn4200Notifications 147 }
    cn4200OSPFIfConfigError NOTIFICATION-TYPE
        OBJECTS {
                    ospfRouterId, -- The originator of the trap
                    ospfIfIpAddress,
                    ospfAddressLessIf,
                    ospfPacketSrc,  -- The source IP address
                    ospfConfigErrorType, -- Type of error
                    ospfPacketType
                  }
        STATUS             current
        DESCRIPTION
           "An ospfIfConfigError  trap  signifies  that  a
           packet  has  been received on a non-virtual in-
           terface  from  a  router  whose   configuration
           parameters  conflict  with this router's confi-
           guration parameters.  Note that the  event  op-
           tionMismatch  should  cause  a  trap only if it
           prevents an adjacency from forming."
                  ::= { cn4200Notifications 148 }


    cn4200OSPFVirtIfConfigError NOTIFICATION-TYPE
        OBJECTS {
                    ospfRouterId, -- The originator of the trap
                    ospfVirtIfAreaId,
                    ospfVirtIfNeighbor,
                    ospfConfigErrorType, -- Type of error
                    ospfPacketType
                  }
        STATUS             current
        DESCRIPTION
           "An ospfConfigError trap signifies that a pack-
           et  has  been  received  on a virtual interface
           from a router  whose  configuration  parameters
           conflict   with   this  router's  configuration
           parameters.  Note that the event optionMismatch
           should  cause a trap only if it prevents an ad-
           jacency from forming."
   ::= { cn4200Notifications 149 }


    cn4200OSPFIfAuthFailure NOTIFICATION-TYPE
        OBJECTS {
                    ospfRouterId, -- The originator of the trap
                    ospfIfIpAddress,
                    ospfAddressLessIf,
                    ospfPacketSrc,  -- The source IP address
                    ospfConfigErrorType, -- authTypeMismatch or
                                         -- authFailure
                    ospfPacketType
                  }
        STATUS             current
        DESCRIPTION
           "An ospfIfAuthFailure  trap  signifies  that  a
           packet  has  been received on a non-virtual in-
           terface from a router whose authentication  key
           or  authentication  type  conflicts  with  this
           router's authentication key  or  authentication
           type."
   ::= { cn4200Notifications 150 }


    cn4200OSPFVirtIfAuthFailure NOTIFICATION-TYPE
        OBJECTS {
                    ospfRouterId, -- The originator of the trap
                    ospfVirtIfAreaId,
                    ospfVirtIfNeighbor,
                    ospfConfigErrorType, -- authTypeMismatch or
                                         -- authFailure
                    ospfPacketType
                  }
        STATUS             current
        DESCRIPTION
           "An ospfVirtIfAuthFailure trap signifies that a
           packet has been received on a virtual interface
           from a router whose authentication key  or  au-
           thentication  type conflicts with this router's
           authentication key or authentication type."
   ::= { cn4200Notifications 151 }


    cn4200OSPFIfRxBadPacket NOTIFICATION-TYPE
        OBJECTS {
                    ospfRouterId, -- The originator of the trap
                    ospfIfIpAddress,
                    ospfAddressLessIf,
                    ospfPacketSrc,  -- The source IP address
                    ospfPacketType
                  }
        STATUS             current
        DESCRIPTION
           "An ospfIfRxBadPacket trap  signifies  that  an
           OSPF  packet has been received on a non-virtual
           interface that cannot be parsed."
   ::= { cn4200Notifications 152 }
    cn4200OSPFVirtIfRxBadPacket NOTIFICATION-TYPE
        OBJECTS {
                    ospfRouterId, -- The originator of the trap
                    ospfVirtIfAreaId,
                    ospfVirtIfNeighbor,
                    ospfPacketType
                  }
        STATUS             current
        DESCRIPTION
           "An ospfRxBadPacket trap signifies that an OSPF
           packet has been received on a virtual interface
           that cannot be parsed."
   ::= { cn4200Notifications 153 }


    cn4200OSPFTxRetransmit NOTIFICATION-TYPE
        OBJECTS {
                    ospfRouterId, -- The originator of the trap
                    ospfIfIpAddress,
                    ospfAddressLessIf,
                    ospfNbrRtrId, -- Destination
                    ospfPacketType,
                    ospfLsdbType,
                    ospfLsdbLsid,
                    ospfLsdbRouterId
                  }
        STATUS             current
        DESCRIPTION
           "An cn4200OSPFTxRetransmit  trap  signifies  than  an
           OSPF  packet  has  been retransmitted on a non-
           virtual interface.  All packets that may be re-
           transmitted  are associated with an LSDB entry.
           The LS type, LS ID, and Router ID are  used  to
           identify the LSDB entry."
   ::= { cn4200Notifications 154 }


    cn4200OSPFVirtIfTxRetransmit NOTIFICATION-TYPE
        OBJECTS {
                    ospfRouterId, -- The originator of the trap
                    ospfVirtIfAreaId,
                    ospfVirtIfNeighbor,
                    ospfPacketType,
                    ospfLsdbType,
                    ospfLsdbLsid,
                    ospfLsdbRouterId
                  }
        STATUS             current
        DESCRIPTION
           "An cn4200OSPFTxRetransmit  trap  signifies  than  an
           OSPF packet has been retransmitted on a virtual
           interface.  All packets that may be retransmit-
           ted  are  associated with an LSDB entry. The LS
           type, LS ID, and Router ID are used to identify
           the LSDB entry."
   ::= { cn4200Notifications 155 }


    cn4200OSPFOriginateLsa NOTIFICATION-TYPE
        OBJECTS {
                    ospfRouterId, -- The originator of the trap
                    ospfLsdbAreaId,  -- 0.0.0.0 for AS Externals
                    ospfLsdbType,
                    ospfLsdbLsid,
                    ospfLsdbRouterId
                  }
        STATUS             current
        DESCRIPTION
           "An cn4200OSPFOriginateLsa trap signifies that a  new
           LSA  has  been originated by this router.  This
           trap should not be invoked for simple refreshes
           of  LSAs  (which happesn every 30 minutes), but
           instead will only be invoked  when  an  LSA  is
           (re)originated due to a topology change.  Addi-
           tionally, this trap does not include LSAs  that
           are  being  flushed  because  they have reached
           MaxAge."
   ::= { cn4200Notifications 156 }


    cn4200OSPFMaxAgeLsa NOTIFICATION-TYPE
        OBJECTS {
                    ospfRouterId, -- The originator of the trap
                    ospfLsdbAreaId,  -- 0.0.0.0 for AS Externals
                    ospfLsdbType,
                    ospfLsdbLsid,
                    ospfLsdbRouterId
                  }
        STATUS             current
        DESCRIPTION
           "An ospfMaxAgeLsa trap signifies  that  one  of
           the LSA in the router's link-state database has
           aged to MaxAge."
   ::= { cn4200Notifications 157 }
    cn4200OSPFLsdbOverflow NOTIFICATION-TYPE
        OBJECTS {
                    ospfRouterId, -- The originator of the trap
                    ospfExtLsdbLimit
                  }
        STATUS             current
        DESCRIPTION
           "An cn4200OSPFLsdbOverflow trap  signifies  that  the
           number of LSAs in the router's link-state data-
           base has exceeded ospfExtLsdbLimit."
   ::= { cn4200Notifications 158 }


    cn4200OSPFLsdbApproachingOverflow NOTIFICATION-TYPE
        OBJECTS {
                    ospfRouterId, -- The originator of the trap
                    ospfExtLsdbLimit
                  }
        STATUS             current
        DESCRIPTION
           "An cn4200OSPFLsdbApproachingOverflow trap  signifies
           that  the  number of LSAs in the router's link-
           state database has exceeded ninety  percent  of
           cn4200OSPFExtLsdbLimit."
   ::= { cn4200Notifications 159 }

    cn4200OSPFIfStateChange NOTIFICATION-TYPE
        OBJECTS {
                    ospfRouterId, -- The originator of the trap
                    ospfIfIpAddress,
                    ospfAddressLessIf,
                    ospfIfState   -- The new state
                  }
        STATUS             current
        DESCRIPTION
           "An cn4200OSPFIfStateChange trap signifies that there
           has been a change in the state of a non-virtual
           OSPF interface. This trap should  be  generated
           when  the interface state regresses (e.g., goes
           from Dr to Down) or progresses  to  a  terminal
           state  (i.e.,  Point-to-Point, DR Other, Dr, or
           Backup)."
   ::= { cn4200Notifications 160 }

-- Enterprise mib traps
	cn4200OSPFAreaSizeThresholdReached	NOTIFICATION-TYPE
		OBJECTS {
			ospfRouterId, -- The originator of the trap
			cnOSPFAreaSizeAreaId
		}
		STATUS	current
		DESCRIPTION
			"Generated when the number of router LSAs of the
			indicated area reaches the Area Size threshold
			configured for that area. NOTE: Support for this trap 
			does not exist."
		::= { cn4200Notifications 161 }

	cn4200OSPFAreaFull	NOTIFICATION-TYPE
		OBJECTS {
			ospfRouterId, -- The originator of the trap
			cnOSPFAreaSizeAreaId
		}
		STATUS	current
		DESCRIPTION
			"Generated when the number of router LSAs of the
			indicated area reaches the maximum area size
			specified for that area. NOTE: Support for this trap does not exist"
		::= { cn4200Notifications 162 }

	cn4200NotificationLOSPTX		NOTIFICATION-TYPE
		OBJECTS		{
			cn4200NotificationHelperPEOID, cn4200NotificationHelperPEType,
			cn4200NotificationHelperAction, cn4200NotificationHelperSev,
			cn4200NotificationDesc, cn4200NotificationHelperServiceIndicator,
			cn4200NotificationAffectedLP, cn4200NotificationAffectedSourceIP,
			cn4200NotificationHelperPEAID, cn4200NotificationHelperConfigChangeSeqNum
		}
		STATUS	current
		DESCRIPTION
			"LOS power on trasmit side."
		::= { cn4200Notifications 163 }


	-- DB Change related traps
	cn4200DBChangeNotificationsPLUGIN	NOTIFICATION-TYPE
		OBJECTS		{
			cn4200NotificationHelperPEOID, cn4200NotificationHelperPEType,
			cn4200NotificationDesc,	cn4200NotificationHelperPEAID,
			cn4200NotificationHelperConfigChangeSeqNum
		}
		STATUS current
		DESCRIPTION
			"Configuration changed due to a plug in of equipment."
		::= { cn4200DBChangeNotifications 1 }

	cn4200DBChangeNotificationsUNPLUG	NOTIFICATION-TYPE
		OBJECTS		{
			cn4200NotificationHelperPEOID, cn4200NotificationHelperPEType,
			cn4200NotificationDesc, cn4200NotificationHelperPEAID,
			cn4200NotificationHelperConfigChangeSeqNum
		}
		STATUS current
		DESCRIPTION
			"Configuration changed due to an unplug of equipment."
		::= { cn4200DBChangeNotifications 2 }

	cn4200DBChangeNotificationsPE	NOTIFICATION-TYPE
		OBJECTS		{
			cn4200NotificationHelperPEOID, cn4200NotificationHelperPEType,
			cn4200NotificationPEPrimaryState, cn4200NotificationPESecondaryState,
			cn4200NotificationDesc, cn4200NotificationHelperPEAID,
			cn4200NotificationHelperConfigChangeSeqNum
		}
		STATUS current
		DESCRIPTION
			"Configuration changed due to add/set/inh/alw of equipment."
		::= { cn4200DBChangeNotifications 3 }

	cn4200DBChangeNotificationsRemPE	NOTIFICATION-TYPE
		OBJECTS		{
			cn4200NotificationHelperPEOID, cn4200NotificationHelperPEType,
			cn4200NotificationDesc, cn4200NotificationHelperPEAID,
			cn4200NotificationHelperConfigChangeSeqNum
		}
		STATUS current
		DESCRIPTION
			"Configuration changed due to removal of equipment."
		::= { cn4200DBChangeNotifications 4 }

	cn4200DBChangeNotificationsSwitchPE	NOTIFICATION-TYPE
		OBJECTS		{
			cn4200NotificationHelperPEOID, cn4200NotificationHelperPEType,
			cn4200NotificationSwitchOverMode, cn4200NotificationDesc,
			cn4200NotificationHelperPEAID,
			cn4200NotificationHelperConfigChangeSeqNum
		}
		STATUS current
		DESCRIPTION
			"Configuration changed due to a switch over of equipment."
		::= { cn4200DBChangeNotifications 5 }

	cn4200DBChangeNotificationsProtPESetting	NOTIFICATION-TYPE
		OBJECTS		{
			cn4200NotificationHelperPEType,
			cn4200NotificationSourceEqptAddr, cn4200NotificationDestEqptAddr,
			cn4200NotificationDesc,
			cn4200NotificationHelperConfigChangeSeqNum
		}
		STATUS current
		DESCRIPTION
			"Configuration changed due to set/delete physical entity fac protection."
		::= { cn4200DBChangeNotifications 6 }

	cn4200DBChangeNotificationsProtPEConfig	NOTIFICATION-TYPE
		OBJECTS		{
			cn4200NotificationHelperPEOID, cn4200NotificationHelperPEType,
			cn4200NotificationDesc, cn4200NotificationHelperPEAID,
			cn4200NotificationHelperConfigChangeSeqNum
		}
		STATUS current
		DESCRIPTION
			"Configuration changed due to alw/inh physical entity fac protection."
		::= { cn4200DBChangeNotifications 7 }

	cn4200DBChangeNotificationsCRS	NOTIFICATION-TYPE
		OBJECTS		{
			cn4200NotificationHelperPEType,
			cn4200NotificationSourceEqptAddr, cn4200NotificationDestEqptAddr,
			cn4200NotificationDesc,
			cn4200NotificationHelperConfigChangeSeqNum
		}
		STATUS current
		DESCRIPTION
			"Configuration changed due to a cross connect of the equipment."
		::= { cn4200DBChangeNotifications 8 }

	cn4200DBChangeNotificationsUpdSNMPTrapSvr	NOTIFICATION-TYPE
		OBJECTS		{
			snmpTrapServerIP,
			snmpTrapServerVersion,
			snmpTrapServerCommunity,
			snmpTrapServerPort,
			cn4200NotificationDesc,
			cn4200NotificationHelperConfigChangeSeqNum
		}
		STATUS current
		DESCRIPTION
			"An SNMP trap server has been added, modified, or deleted."
		::= { cn4200DBChangeNotifications 9 }

	cn4200DBChangeNotificationsUpdSNMPCommunity	NOTIFICATION-TYPE
		OBJECTS		{
			snmpServerCommunityHost,
			snmpServerCommunityValue,
			snmpServerCommunityAccessType,
			cn4200NotificationDesc,
			cn4200NotificationHelperConfigChangeSeqNum
		}
		STATUS current
		DESCRIPTION
			"SNMP community updated."
		::= { cn4200DBChangeNotifications 10 }

	cn4200DBChangeNotificationsUpdNameSvr	NOTIFICATION-TYPE
		OBJECTS		{
			nameServerIP,
			cn4200NotificationDesc,
			cn4200NotificationHelperConfigChangeSeqNum
		}
		STATUS current
		DESCRIPTION
			"A name server has been added or deleted."
		::= { cn4200DBChangeNotifications 11 }

	cn4200DBChangeNotificationsUpdDNS		NOTIFICATION-TYPE
		OBJECTS		{
			domainServerName,
			cn4200NotificationDesc,
			cn4200NotificationHelperConfigChangeSeqNum
		}
		STATUS current
		DESCRIPTION
			"A DNS server has been added or deleted."
		::= { cn4200DBChangeNotifications 12 }

	cn4200DBChangeNotificationsUpdRadiusSvr	NOTIFICATION-TYPE
		OBJECTS		{
			radiusServerIP,
			radiusServerSecret,
			radiusServerTimeout,
			cn4200NotificationDesc,
			cn4200NotificationHelperConfigChangeSeqNum
		}
		STATUS current
		DESCRIPTION
			"Radius server added or modified."
		::= { cn4200DBChangeNotifications 13 }

	cn4200DBChangeNotificationsDelRadiusSvr	NOTIFICATION-TYPE
		OBJECTS		{
			radiusServerIP,
			cn4200NotificationDesc,
			cn4200NotificationHelperConfigChangeSeqNum
		}
		STATUS current
		DESCRIPTION
			"Radius server deleted."
		::= { cn4200DBChangeNotifications 14 }

	cn4200DBChangeNotificationsUpdNTPSvr	NOTIFICATION-TYPE
		OBJECTS		{
			ntpServerIP,
			ntpServerKey,
			ntpServerVersion,
			cn4200NotificationDesc,
			cn4200NotificationHelperConfigChangeSeqNum
		}
		STATUS current
		DESCRIPTION
			"NTP server added or deleted."
		::= { cn4200DBChangeNotifications 15 }

	cn4200DBChangeNotificationsDelNTPSvr	NOTIFICATION-TYPE
		OBJECTS		{
			ntpServerIP,
			cn4200NotificationDesc,
			cn4200NotificationHelperConfigChangeSeqNum
		}
		STATUS current
		DESCRIPTION
			"NTP server deleted."
		::= { cn4200DBChangeNotifications 16 }

	cn4200DBChangeNotificationsUpdNTPAuthKey	NOTIFICATION-TYPE
		OBJECTS		{
			ntpAuthKeyId,
			ntpAuthKeyValue,
			cn4200NotificationDesc,
			cn4200NotificationHelperConfigChangeSeqNum
		}
		STATUS current
		DESCRIPTION
			"NTP autoroization key updated."
		::= { cn4200DBChangeNotifications 17 }

	cn4200DBChangeNotificationsDelNTPAuthKey	NOTIFICATION-TYPE
		OBJECTS		{
			ntpAuthKeyId,
			cn4200NotificationDesc,
			cn4200NotificationHelperConfigChangeSeqNum
		}
		STATUS current
		DESCRIPTION
			"NTP autoroization key deleted."
		::= { cn4200DBChangeNotifications 18 }

	cn4200DBChangeNotificationsUpdNTPTrustKey	NOTIFICATION-TYPE
		OBJECTS		{
			ntpTrustedKeyId,
			cn4200NotificationDesc,
			cn4200NotificationHelperConfigChangeSeqNum
		}
		STATUS current
		DESCRIPTION
			"NTP authority key updated."
		::= { cn4200DBChangeNotifications 19 }

	cn4200DBChangeNotificationsUpdTADRMap	NOTIFICATION-TYPE
		OBJECTS		{
			gslamAGTAdrMapName,
			gslamAGTAdrMapIP,
			gslamAGTAdrMapPortNumber,
			cn4200NotificationDesc,
			cn4200NotificationHelperConfigChangeSeqNum
		}
		STATUS current
		DESCRIPTION
			"TADR map updated."
		::= { cn4200DBChangeNotifications 20 }

	cn4200DBChangeNotificationsDelTADRMap	NOTIFICATION-TYPE
		OBJECTS		{
			gslamAGTAdrMapName,
			cn4200NotificationDesc,
			cn4200NotificationHelperConfigChangeSeqNum
		}
		STATUS current
		DESCRIPTION
			"TADR map deleted."
		::= { cn4200DBChangeNotifications 21 }

	cn4200DBChangeNotificationsUpdECCRoute	NOTIFICATION-TYPE
		OBJECTS		{
			cn4200NotificationHelperDestNetwork,
			cn4200NotificationHelperGateway,
			cn4200NotificationHelperNetmask,
			cn4200NotificationHelperMetric,
			cn4200NotificationDesc,
			cn4200NotificationHelperConfigChangeSeqNum
		}
		STATUS current
		DESCRIPTION
			"ECC route updated."
		::= { cn4200DBChangeNotifications 22 }

	cn4200DBChangeNotificationsUpdSID	NOTIFICATION-TYPE
		OBJECTS		{
			cn4200NotificationHelperSID,
			cn4200NotificationDesc,
			cn4200NotificationHelperConfigChangeSeqNum
		}
		STATUS current
		DESCRIPTION
			"SID updated."
		::= { cn4200DBChangeNotifications 23 }

	-- ******************* R5.0 *******************

	cn4200DBChangeNotificationsPORTASSOC	NOTIFICATION-TYPE
		OBJECTS		{
			cn4200NotificationHelperPEType,
			cn4200NotificationSourceEqptAddr, cn4200NotificationDestEqptAddr,
			gslamAGREL50ROADMPortAssocType, gslamAGREL50ROADMPortAssocDCMType,
			gslamAGREL50ROADMPortAssocDCMDispersion,
			gslamAGREL50ROADMPortAssocPadAttenuation,
			cn4200NotificationDesc,
			cn4200NotificationHelperPETypeSrc,
			cn4200NotificationHelperPETypeDst,
            cn4200NotificationHelperPEAIDSrc,
            cn4200NotificationHelperPEAIDDst,
			cn4200NotificationHelperConfigChangeSeqNum
		}
		STATUS deprecated 
		DESCRIPTION
			"Trap for add/delete/modify of Port Assoc"
		::= { cn4200DBChangeNotifications 24 }

	cn4200DBChangeNotificationsWC	NOTIFICATION-TYPE
		OBJECTS		{
			cn4200NotificationHelperPEType,
			cn4200NotificationSourceEqptAddr, cn4200NotificationDestEqptAddr,
			gslamAGREL50ROADMOpticalCXDirection, 
			gslamAGREL50ROADMOpticalCXCktID,
			gslamAGREL50ROADMOpticalCXNature,
			cn4200NotificationDesc,
			cn4200NotificationHelperConfigChangeSeqNum
		}
		STATUS current
		DESCRIPTION
			"Trap for add/delete/Modify of OXCON"
		::= { cn4200DBChangeNotifications 25 }

	cn4200DBChangeNotificationsVOA	NOTIFICATION-TYPE
		OBJECTS		{
			gslamAGREL50IOModuleVoaIndex,
			gslamAGREL50IOModuleVoaAttenuation,
			cn4200NotificationHelperPEAID,
			cn4200NotificationDesc,
			cn4200NotificationHelperConfigChangeSeqNum
		}
		STATUS current
		DESCRIPTION
			" Voa attenuation done for a module"
		::= { cn4200DBChangeNotifications 26 }

	cn4200DBChangeNotificationsPORTOPTPWRCTRL	NOTIFICATION-TYPE
		OBJECTS		{
			gslamAGREL50PortOptPwrCtrl,
			cn4200NotificationHelperPEAID,
			cn4200NotificationHelperConfigChangeSeqNum
		}
		STATUS current
		DESCRIPTION
			"optical pwr ctrl added for OPS/OTS port"
		::= { cn4200DBChangeNotifications 27 }

	cn4200DBChangeNotificationsCHNLOPTPWRCTRL	NOTIFICATION-TYPE
		OBJECTS		{
			gslamAGREL50ChannelOptPwrCtrl,
			cn4200NotificationHelperPEAID,
			cn4200NotificationHelperConfigChangeSeqNum
		}
		STATUS current
		DESCRIPTION
			"optical pwr ctrl added for occ chnl"
		::= { cn4200DBChangeNotifications 28 }

    cn4200DBChangeNotificationsPORTASSOC2    NOTIFICATION-TYPE
        OBJECTS     {
            cn4200NotificationHelperPEType,
            cn4200NotificationSourceEqptAddr, cn4200NotificationDestEqptAddr,
            gslamAGREL50ROADMPortAssocType, 
            gslamAGREL50ROADMPortAssocPadAttenuation,
            cn4200NotificationDesc,
            cn4200NotificationHelperPETypeSrc,
            cn4200NotificationHelperPETypeDst,
            cn4200NotificationHelperPEAIDSrc,
            cn4200NotificationHelperPEAIDDst,
	    cn4200NotificationHelperConfigChangeSeqNum
        }   
        STATUS current
        DESCRIPTION
            "Trap for add/delete/modify of Port Assoc"
        ::= { cn4200DBChangeNotifications 29 }

    cn4200DBChangeNotificationsSnmpMode    NOTIFICATION-TYPE
        OBJECTS     {
            snmpServiceMode,
				cn4200NotificationHelperConfigChangeSeqNum
        }   
        STATUS current
        DESCRIPTION
            "Trap for modification of Snmp Mode"
        ::= { cn4200DBChangeNotifications 30 }

    cn4200DBChangeNotificationsServiceStatus    NOTIFICATION-TYPE
        OBJECTS     {
            cn4200NotificationHelperDaemon,
            cn4200NotificationHelperAdminState,
				cn4200NotificationHelperConfigChangeSeqNum
        }   
        STATUS current
        DESCRIPTION
            "Trap for modification of Service status"
        ::= { cn4200DBChangeNotifications 31 }

	-- Set Fail traps


	-- Set Fail traps
	gslamAGSetFailNotificationEntCRS	NOTIFICATION-TYPE
		OBJECTS		{
			cn4200NotificationLPID, cn4200NotificationCktID, cn4200NotificationHelperPEType,
			cn4200NotificationSourceEqptAddr, cn4200NotificationDestEqptAddr,
			cn4200NotificationDesc, cn4200NotificationFailureReason
		}
		STATUS current
		DESCRIPTION
			"Failed to enter a cross connect of the equipment."
		::= { cn4200SetFailNotifications 1 }

	cn4200SetFailNotificationDelCRS	NOTIFICATION-TYPE
		OBJECTS		{
			cn4200NotificationLPID, cn4200NotificationCktID, cn4200NotificationHelperPEType,
			cn4200NotificationSourceEqptAddr, cn4200NotificationDestEqptAddr,
			cn4200NotificationDesc, cn4200NotificationFailureReason
		}
		STATUS current
		DESCRIPTION
			"Failed to delete a cross connect of the equipment."
		::= { cn4200SetFailNotifications 2 }

	cn4200SetFailNotificationEdCRS	NOTIFICATION-TYPE
		OBJECTS		{
			cn4200NotificationLPID, cn4200NotificationCktID, cn4200NotificationHelperPEType,
			cn4200NotificationSourceEqptAddr, cn4200NotificationDestEqptAddr,
			cn4200NotificationDesc, cn4200NotificationFailureReason
		}
		STATUS current
		DESCRIPTION
			"Failed to edit a cross connect of the equipment."
		::= { cn4200SetFailNotifications 3 }

	cn4200SetFailNotificationEntProt	NOTIFICATION-TYPE
		OBJECTS		{
			cn4200NotificationLPID, cn4200NotificationHelperPEType,
			cn4200NotificationSourceEqptAddr, cn4200NotificationDestEqptAddr,
			cn4200NotificationDesc, cn4200NotificationFailureReason
		}
		STATUS current
		DESCRIPTION
			"Failed to enter a protection group of the equipment."
		::= { cn4200SetFailNotifications 4 }

	cn4200SetFailNotificationDelProt	NOTIFICATION-TYPE
		OBJECTS		{
			cn4200NotificationLPID, cn4200NotificationHelperPEType,
			cn4200NotificationSourceEqptAddr, cn4200NotificationDestEqptAddr,
			cn4200NotificationDesc, cn4200NotificationFailureReason
		}
		STATUS current
		DESCRIPTION
			"Failed to delete a protection group of the equipment."
		::= { cn4200SetFailNotifications 5 }

	cn4200SetFailNotificationEdProt	NOTIFICATION-TYPE
		OBJECTS		{
			cn4200NotificationLPID, cn4200NotificationHelperPEType,
			cn4200NotificationSourceEqptAddr, cn4200NotificationDestEqptAddr,
			cn4200NotificationDesc, cn4200NotificationFailureReason
		}
		STATUS current
		DESCRIPTION
			"Failed to edit a protection group of the equipment."
		::= { cn4200SetFailNotifications 6 }

	cn4200SetFailNotificationProtSwitch	NOTIFICATION-TYPE
		OBJECTS		{
			cn4200NotificationLPID, cn4200NotificationHelperPEType,
			cn4200NotificationSourceEqptAddr, cn4200NotificationDestEqptAddr,
			cn4200NotificationDesc, cn4200NotificationFailureReason
		}
		STATUS current
		DESCRIPTION
			"Failed to perform protection switch."
		::= { cn4200SetFailNotifications 7 }

	cn4200SetFailNotificationAlwSwDx	NOTIFICATION-TYPE
		OBJECTS		{
			cn4200NotificationLPID, cn4200NotificationHelperPEType,
			cn4200NotificationSourceEqptAddr, cn4200NotificationDestEqptAddr,
			cn4200NotificationDesc, cn4200NotificationFailureReason
		}
		STATUS current
		DESCRIPTION
			"Failed to allow duplex switching."
		::= { cn4200SetFailNotifications 8 }

	cn4200SetFailNotificationInhSwDx	NOTIFICATION-TYPE
		OBJECTS		{
			cn4200NotificationLPID, cn4200NotificationHelperPEType,
			cn4200NotificationSourceEqptAddr, cn4200NotificationDestEqptAddr,
			cn4200NotificationDesc, cn4200NotificationFailureReason
		}
		STATUS current
		DESCRIPTION
			"Failed to inhibit duplex switching."
		::= { cn4200SetFailNotifications 9 }

	cn4200SetFailNotificationInitSys	NOTIFICATION-TYPE
		OBJECTS		{
			cn4200NotificationHelperPEType, cn4200NotificationHelperPEOID,
			cn4200NotificationDesc, cn4200NotificationFailureReason,
			cn4200NotificationHelperPEAID
		}
		STATUS current
		DESCRIPTION
			"Failed to perform system init."
		::= { cn4200SetFailNotifications 10 }

	cn4200SetFailNotificationEntEqpt	NOTIFICATION-TYPE
		OBJECTS		{
			cn4200NotificationHelperPEType, cn4200NotificationHelperPEOID,
			cn4200NotificationDesc, cn4200NotificationFailureReason,
			cn4200NotificationHelperPEAID
		}
		STATUS current
		DESCRIPTION
			"Failed to enter an equipment object."
		::= { cn4200SetFailNotifications 11 }

	cn4200SetFailNotificationDelEqpt	NOTIFICATION-TYPE
		OBJECTS		{
			cn4200NotificationHelperPEType, cn4200NotificationHelperPEOID,
			cn4200NotificationDesc, cn4200NotificationFailureReason,
			cn4200NotificationHelperPEAID
		}
		STATUS current
		DESCRIPTION
			"Failed to delete an equipment object."
		::= { cn4200SetFailNotifications 12 }

	cn4200SetFailNotificationEdEqpt	NOTIFICATION-TYPE
		OBJECTS		{
			cn4200NotificationHelperPEType, cn4200NotificationHelperPEOID,
			cn4200NotificationDesc, cn4200NotificationFailureReason,
			cn4200NotificationHelperPEAID
		}
		STATUS current
		DESCRIPTION
			"Failed to edit an equipment object."
		::= { cn4200SetFailNotifications 13 }

	cn4200SetFailNotificationRmvEqpt	NOTIFICATION-TYPE
		OBJECTS		{
			cn4200NotificationHelperPEType, cn4200NotificationHelperPEOID,
			cn4200NotificationDesc, cn4200NotificationFailureReason,
			cn4200NotificationHelperPEAID
		}
		STATUS current
		DESCRIPTION
			"Failed to place an equipment object in a maintenance state."
		::= { cn4200SetFailNotifications 14 }

	cn4200SetFailNotificationRstEqpt	NOTIFICATION-TYPE
		OBJECTS		{
			cn4200NotificationHelperPEType, cn4200NotificationHelperPEOID,
			cn4200NotificationDesc, cn4200NotificationFailureReason,
			cn4200NotificationHelperPEAID
		}
		STATUS current
		DESCRIPTION
			"Failed to place an equipment object in an in-service state."
		::= { cn4200SetFailNotifications 15 }

	cn4200SetFailNotificationOprLpbk	NOTIFICATION-TYPE
		OBJECTS		{
			cn4200NotificationHelperPEType, cn4200NotificationHelperPEOID,
			cn4200NotificationDesc, cn4200NotificationFailureReason,
			cn4200NotificationHelperPEAID
		}
		STATUS current
		DESCRIPTION
			"Failed to configure a loopback on the specified object."
		::= { cn4200SetFailNotifications 16 }

	cn4200SetFailNotificationRlsLpbk	NOTIFICATION-TYPE
		OBJECTS		{
			cn4200NotificationHelperPEType, cn4200NotificationHelperPEOID,
			cn4200NotificationDesc, cn4200NotificationFailureReason,
			cn4200NotificationHelperPEAID
		}
		STATUS current
		DESCRIPTION
			"Failed to realise a loopback on the specified object."
		::= { cn4200SetFailNotifications 17 }


END
